/*
  MemNet implementation allocate — SSOT parts → live code in this checkout.

  One Hatch wheel (memnet-llm) for many hosts (droplet + devices).
  MemNet MCP module = tip/ops (tip≠face). Cousin sysmledge is NOT
  allocated here (thisRepoHasProductFace=false; mustNotInventUploadBind).
  Not N-server federation (#47). LAN MCP front catalogue (#191) stays
  invent-only (MemNetLanMcpFront / ClusterRoute / SnapshotHandCarry).
  SliceHandCarry (#47 cousin / MN-REQ-06.10) is invent-only; MUST NOT
  allocate a Python path for that copy. MemNetProductGateway
  (MN-REQ-06.12) is the shipped memnet-mcp capability and IS allocated.
*/
package MemNetImplementation {
  private import ScalarValues::*;
  private import MemNetRequirements::*;
  private import MemNet::*;

  allocation def SoftwareAllocate {
    doc /*
      Logical SysML part (SSOT) → code module on disk.
      Source end = logical; target end = code. Many hosts bind the
      same wheel; hosts are not extra packages.
    */
    end logical;
    end code;
  }

  part def CodeModule {
    doc /*
      Live Python module or package directory in this repo.
      Tracking record: implemented=true and inThisRepo=true means
      the path exists here; track=true means honesty tests watch it.
    */
    attribute path : String;
    attribute pyName : String;
    attribute implemented : Boolean = true;
    attribute inThisRepo : Boolean = true;
    attribute track : Boolean = true;
  }

  part def ImplementationTracker {
    doc /*
      Implementation ledger. Each SoftwareAllocate row tracks one
      SSOT part to a live path. Derived map:
      sysml-models/outputs/ssot-to-code-allocate-map.md
      Cue TSK_model_alloc / qname=MemNetImplementation. A missing
      path fails honesty tests — that is the tracker. MUST NOT
      track cousin sysmledge (sysmlEdgeTracked=false).
    */
    attribute trackAllocateRows : Boolean = true;
    attribute mapPath : String = "sysml-models/outputs/ssot-to-code-allocate-map.md";
    attribute sysmlEdgeTracked : Boolean = false;
    attribute missingPathFailsCi : Boolean = true;

    satisfy MN_REQ_00_MissionBridge::MN_REQ_06_ProcessBoundary::MN_REQ_06_7_SsotToCodeAllocate;
  }

  // ----- Wheel (one package, many hosts) -----

  part def CoreLibraryMod {
    attribute path : String = "parts/common/memnet/memnet";
    attribute pyName : String = "memnet";
    attribute hatchTarget : String = "parts/common/memnet/memnet";
    attribute implemented : Boolean = true;
    attribute inThisRepo : Boolean = true;
    attribute track : Boolean = true;
  }

  part def McpServerMod {
    doc /*
      memnet-mcp console: memnet_mcp.entry:main, which checks the [mcp]
      extra (mcp.server.fastmcp, then uvicorn) before it parses any
      argument and then runs memnet_mcp.server main (MN-REQ-06.18). A
      missing module gives one stderr line, @ERR: mcp_extra_missing|...;
      install with: pip install 'memnet-llm[mcp]', and exit 2, for every
      transport and for --help (tests/test_mcp_extra_missing.py).
      Streamable-http is stateless with JSON replies (FastMCP
      stateless_http, json_response; MN-REQ-06.19): a restart drops no
      MCP session.
      Tip/ops engine face. MUST NOT be taught as product invent face
      (tipIsFace=false).
    */
    attribute path : String = "parts/memnet-mcp/software/memnet_mcp/server.py";
    attribute pyName : String = "memnet_mcp.server";
    attribute consoleEntry : String = "memnet_mcp.entry:main";
    attribute entryPyName : String = "memnet_mcp.entry";
    attribute mcpExtraHint : String = "pip install 'memnet-llm[mcp]'";
    attribute errMcpExtraMissing : String = "mcp_extra_missing";
    attribute mcpExtraMissingExit : Integer = 2;
    attribute extraCheckBeforeArgs : Boolean = true;
    attribute everyTransportNeedsExtra : Boolean = true;
    attribute statelessHttp : Boolean = true;
    attribute jsonResponse : Boolean = true;
    attribute tipIsFace : Boolean = false;
    attribute implemented : Boolean = true;
    attribute inThisRepo : Boolean = true;
    attribute track : Boolean = true;

    satisfy MN_REQ_00_MissionBridge::MN_REQ_06_ProcessBoundary::MN_REQ_06_18_McpExtraFailFast;
    satisfy MN_REQ_00_MissionBridge::MN_REQ_06_ProcessBoundary::MN_REQ_06_19_RestartSafeTransport;
  }

  part def MemNetLlmWheel {
    doc /*
      Hatch memnet-llm. Droplet and device hosts instantiate this
      same wheel. MUST NOT nest a SysMLEdge product face in the wheel.
    */
    part core : CoreLibraryMod;
    part mcp : McpServerMod;
    attribute hatchPackage : String = "memnet-llm";
    attribute hatchCorePackage : String = "parts/common/memnet/memnet";
    attribute hatchMcpPackage : String = "parts/memnet-mcp/software/memnet_mcp";
    attribute consoleMemnet : String = "memnet.cli:main";
    attribute consoleMemnetMcp : String = "memnet_mcp.entry:main";
    attribute oneWheelManyHosts : Boolean = true;
    attribute sysmlEdgeInWheel : Boolean = false;
    attribute track : Boolean = true;

    satisfy MN_REQ_00_MissionBridge::MN_REQ_06_ProcessBoundary::MN_REQ_06_7_SsotToCodeAllocate;
  }

  // ----- Engine modules (names match SysML part defs) -----

  part def InProcessEngineMod {
    attribute path : String = "parts/common/memnet/memnet/in_process_engine.py";
    attribute pyName : String = "memnet.in_process_engine";
  }
  part def LocalIpcGatewayMod {
    attribute path : String = "parts/common/memnet/memnet/local_ipc_gateway.py";
    attribute pyName : String = "memnet.local_ipc_gateway";
  }
  part def TcpServeBridgeMod {
    attribute path : String = "parts/common/memnet/memnet/tcp_serve_bridge.py";
    attribute pyName : String = "memnet.tcp_serve_bridge";
  }
  part def ServeDaemonMod {
    attribute path : String = "parts/common/memnet/memnet/serve.py";
    attribute pyName : String = "memnet.serve";
  }
  part def AdminUsageReportMod {
    doc /* Admin-only serve usage report (MN-REQ-06.11); not agent MCP. */
    attribute path : String = "parts/common/memnet/memnet/admin_usage.py";
    attribute pyName : String = "memnet.admin_usage";
  }
  part def SafeUpgradeMod {
    doc /*
      Serve drain, manifest, startup restore, and retire (MN-REQ-06.14).
      Start-up restore from the newest valid snapshot set, checkpoint or
      upgrade-prepare, on every start (MN-REQ-06.17; restore_candidates,
      restore_manifest, startup_restore_or_exit; runtime tests
      tests/test_restart_restore.py, tests/test_safe_upgrade.py). Retire
      is an audit mark; a retired manifest stays a candidate.
    */
    attribute path : String = "parts/common/memnet/memnet/upgrade.py";
    attribute pyName : String = "memnet.upgrade";
    attribute implemented : Boolean = true;
    attribute restoresCheckpointSet : Boolean = true;
    attribute restoresUpgradeSet : Boolean = true;
    attribute tieGoesToUpgrade : Boolean = true;
    attribute retiredStaysCandidate : Boolean = true;
    attribute laterRestartRestores : Boolean = true;
    attribute preflightBeforeLoad : Boolean = true;
    attribute warnRestoreFallback : String = "restore_fallback";
    attribute fallbackIsLoud : Boolean = true;
    attribute statRestoreSource : String = "restore_source";
    attribute printsRestoreSource : Boolean = true;
    attribute noneValidExit : Integer = 3;
    attribute noCandidateSkipped : Boolean = true;
    attribute loadFailureFallsBack : Boolean = false;
    attribute emptyNewestSetWins : Boolean = true;
    attribute retireOnlyUpgradeSource : Boolean = true;
    attribute writesCheckpointManifest : Boolean = false;

    perform action startRestore : MemNetBehaviour::RestartRestoreChoice;

    satisfy MN_REQ_00_MissionBridge::MN_REQ_06_ProcessBoundary::MN_REQ_06_17_RestartRestoreNewestSet;
  }
  part def ServeRetryMod {
    doc /*
      Restart-safe client retry (MN-REQ-06.19). One READ / WRITE
      classification of serve requests (argv_kind, request_kind;
      unknown is WRITE), the serve_draining retry_after parse, the
      MEMNET_SERVE_RETRY_S budget and jittered backoff. The loop is
      ServePool.send (memnet/serve_pool.py); send_command, the product
      gateway and the memnet-mcp tcp client all go through it.
    */
    attribute path : String = "parts/common/memnet/memnet/serve_retry.py";
    attribute pyName : String = "memnet.serve_retry";
    attribute poolPath : String = "parts/common/memnet/memnet/serve_pool.py";
    attribute implemented : Boolean = true;
    attribute budgetEnv : String = "MEMNET_SERVE_RETRY_S";
    attribute defaultBudgetS : Real = 30.0;
    attribute backoffBaseS : Real = 0.1;
    attribute backoffCapS : Real = 2.0;
    attribute retriesNotDelivered : Boolean = true;
    attribute honoursRetryAfter : Boolean = true;
    attribute retriesReadAfterSend : Boolean = true;
    attribute replaysWriteAfterSend : Boolean = false;
    attribute unknownVerbIsWrite : Boolean = true;
    attribute gatewayProbeGate : Boolean = false;
    attribute nestedRetryLoops : Integer = 1;

    perform action retryChoice : MemNetBehaviour::ServeRetryChoice;

    satisfy MN_REQ_00_MissionBridge::MN_REQ_06_ProcessBoundary::MN_REQ_06_19_RestartSafeTransport;
  }
  part def ServeCheckpointMod {
    doc /* Admin checkpoint of loaded sessions without drain (MN-REQ-06.15). */
    attribute path : String = "parts/common/memnet/memnet/checkpoint.py";
    attribute pyName : String = "memnet.checkpoint";
  }
  part def SnapshotAclMod {
    doc /*
      Session ACL in session save / load (MN-REQ-06.16): the #@ACL:
      line and @SNAP version 2 in snapshot.py. The shared ACL serialiser
      is acl.py (also used by the upgrade passport); the bind stores a
      SHA-256 lease digest there. Snapshot and manifest writes go through
      atomic_file.py (0600 temp, fsync, rename).
    */
    attribute path : String = "parts/common/memnet/memnet/snapshot.py";
    attribute pyName : String = "memnet.snapshot";

    satisfy MN_REQ_00_MissionBridge::MN_REQ_06_ProcessBoundary::MN_REQ_06_16_SnapshotAcl;
  }
  part def CliFacadeMod {
    attribute path : String = "parts/common/memnet/memnet/cli.py";
    attribute pyName : String = "memnet.cli";
    attribute consoleEntry : String = "memnet.cli:main";
  }
  part def SessionLifecycleMod {
    attribute path : String = "parts/common/memnet/memnet/session_lifecycle.py";
    attribute pyName : String = "memnet.session_lifecycle";
  }
  part def GraphStoreMod {
    attribute path : String = "parts/common/memnet/memnet/graph_store.py";
    attribute pyName : String = "memnet.graph_store";
  }
  part def MemStoreMod {
    doc /* Backing store aliased with GraphStore (system-design-notes). */
    attribute path : String = "parts/common/memnet/memnet/mem_store.py";
    attribute pyName : String = "memnet.mem_store";
  }
  part def CapsPolicyMod {
    attribute path : String = "parts/common/memnet/memnet/caps_policy.py";
    attribute pyName : String = "memnet.caps_policy";
  }
  part def CapsAclMod {
    doc /* CapsPolicy ACL who / pin_map-vs-mutate / scope (acl.py). */
    attribute path : String = "parts/common/memnet/memnet/acl.py";
    attribute pyName : String = "memnet.acl";
  }
  part def GqlCodecMod {
    attribute path : String = "parts/common/memnet/memnet/gql_codec.py";
    attribute pyName : String = "memnet.gql_codec";
  }
  part def ProductGqlGateMod {
    doc /* Product gate + leftover lowering (memnet.gql); not GraphGlot parse. */
    attribute path : String = "parts/common/memnet/memnet/gql.py";
    attribute pyName : String = "memnet.gql";
  }
  part def GraphGlotParseFrontMod {
    attribute path : String = "parts/common/memnet/memnet/gql_parse_front.py";
    attribute pyName : String = "memnet.gql_parse_front";
  }
  part def MutateGateMod {
    attribute path : String = "parts/common/memnet/memnet/mutate_gate.py";
    attribute pyName : String = "memnet.mutate_gate";
  }
  part def PinMapComposerMod {
    doc /* PinMapShapedRead + BoundedMatchFind (FindResult). */
    attribute path : String = "parts/common/memnet/memnet/pin_map_composer.py";
    attribute pyName : String = "memnet.pin_map_composer";
  }
  part def PeakLMod {
    attribute path : String = "parts/common/memnet/memnet/peak_l.py";
    attribute pyName : String = "memnet.peak_l";
  }
  part def NeighbourhoodReserveMod {
    attribute path : String = "parts/common/memnet/memnet/neighbourhood_reserve.py";
    attribute pyName : String = "memnet.neighbourhood_reserve";
  }
  part def SameThingAbsorbMod {
    attribute path : String = "parts/common/memnet/memnet/same_thing_absorb.py";
    attribute pyName : String = "memnet.same_thing_absorb";
  }
  part def ImportAbsorbMod {
    attribute path : String = "parts/common/memnet/memnet/import_absorb.py";
    attribute pyName : String = "memnet.import_absorb";
  }
  part def CheapLlmImportGuardMod {
    attribute path : String = "parts/common/memnet/memnet/cheap_llm_import_guard.py";
    attribute pyName : String = "memnet.cheap_llm_import_guard";
  }
  part def PinMapIngestMod {
    attribute path : String = "parts/common/memnet/memnet/pin_map_ingest.py";
    attribute pyName : String = "memnet.pin_map_ingest";
  }
  part def PinMapExportMod {
    attribute path : String = "parts/common/memnet/memnet/pin_map_export.py";
    attribute pyName : String = "memnet.pin_map_export";
  }
  part def CatalogSnapMod {
    attribute path : String = "parts/common/memnet/memnet/catalog_snap.py";
    attribute pyName : String = "memnet.catalog_snap";
  }
  part def AgensGraphAdapterMod {
    attribute path : String = "parts/common/memnet/memnet/durable/agensgraph.py";
    attribute pyName : String = "memnet.durable.agensgraph";
  }
  part def RagHostHookMod {
    attribute path : String = "parts/common/memnet/memnet/rag_host_hook.py";
    attribute pyName : String = "memnet.rag_host_hook";
  }
  part def SchemaRegistryMod {
    attribute path : String = "parts/common/memnet/memnet/schema_registry.py";
    attribute pyName : String = "memnet.schema_registry";
  }
  part def SnapshotStoreMod {
    attribute path : String = "parts/common/memnet/memnet/snapshot_store.py";
    attribute pyName : String = "memnet.snapshot_store";
  }
  part def HousekeepSettleMod {
    attribute path : String = "parts/common/memnet/memnet/housekeep_settle.py";
    attribute pyName : String = "memnet.housekeep_settle";
  }

  // ----- MCP surface modules -----

  part def McpFacadeMod {
    attribute path : String = "parts/memnet-mcp/software/memnet_mcp/mcp_facade.py";
    attribute pyName : String = "memnet_mcp.mcp_facade";
  }
  part def McpServeBridgeMod {
    attribute path : String = "parts/memnet-mcp/software/memnet_mcp/serve_bridge.py";
    attribute pyName : String = "memnet_mcp.serve_bridge";
  }
  part def LawSeedHelperMod {
    attribute path : String = "parts/memnet-mcp/software/memnet_mcp/law_seed_helper.py";
    attribute pyName : String = "memnet_mcp.law_seed_helper";
  }
  part def McpHttpTransportMod {
    doc /* Opt-in streamable-http; Multitask shared store with TCP. */
    attribute path : String = "parts/memnet-mcp/software/memnet_mcp/http_transport.py";
    attribute pyName : String = "memnet_mcp.http_transport";
  }
  part def ProductGatewayMod {
    doc /* Product gateway on memnet-mcp (MN-REQ-06.12). Not mn_tip_. */
    attribute path : String = "parts/memnet-mcp/software/memnet_mcp/product_gateway.py";
    attribute pyName : String = "memnet_mcp.product_gateway";
    attribute tipIsFace : Boolean = false;
    attribute reusesTipBearer : Boolean = false;
  }

  // ----- Cousin product face: NOT in this repo -----

  part def CousinSysMLEdgeNotInRepo {
    doc /*
      Product invent face is sysmledge (cousin). This MemNet checkout
      MUST NOT allocate or invent that upload/bind path.
    */
    attribute pyName : String = "sysmledge";
    attribute implemented : Boolean = false;
    attribute inThisRepo : Boolean = false;
    attribute track : Boolean = false;
    attribute mustNotInventUploadBind : Boolean = true;
  }

  // ----- Usages -----

  part wheel : MemNetLlmWheel;
  part inProcessMod : InProcessEngineMod;
  part ipcMod : LocalIpcGatewayMod;
  part tcpMod : TcpServeBridgeMod;
  part serveDaemonMod : ServeDaemonMod;
  part adminUsageMod : AdminUsageReportMod;
  part safeUpgradeMod : SafeUpgradeMod;
  part serveCheckpointMod : ServeCheckpointMod;
  part serveRetryMod : ServeRetryMod;
  part snapAclMod : SnapshotAclMod;
  part cliMod : CliFacadeMod;
  part sessionsMod : SessionLifecycleMod;
  part storeMod : GraphStoreMod;
  part memStoreMod : MemStoreMod;
  part capsMod : CapsPolicyMod;
  part capsAclMod : CapsAclMod;
  part gqlMod : GqlCodecMod;
  part gqlPyMod : ProductGqlGateMod;
  part parseFrontMod : GraphGlotParseFrontMod;
  part mutateMod : MutateGateMod;
  part pinMapMod : PinMapComposerMod;
  part peakLMod : PeakLMod;
  part rsvMod : NeighbourhoodReserveMod;
  part sameThingMod : SameThingAbsorbMod;
  part absorbMod : ImportAbsorbMod;
  part cheapLlmMod : CheapLlmImportGuardMod;
  part ingestMod : PinMapIngestMod;
  part exportMod : PinMapExportMod;
  part catalogMod : CatalogSnapMod;
  part agensMod : AgensGraphAdapterMod;
  part ragHookMod : RagHostHookMod;
  part schemaMod : SchemaRegistryMod;
  part snapMod : SnapshotStoreMod;
  part housekeepMod : HousekeepSettleMod;
  part mcpFacadeMod : McpFacadeMod;
  part mcpBridgeMod : McpServeBridgeMod;
  part lawSeedMod : LawSeedHelperMod;
  part mcpHttpMod : McpHttpTransportMod;
  part productGatewayMod : ProductGatewayMod;
  part sysmlEdgeAbsent : CousinSysMLEdgeNotInRepo;
  part tracker : ImplementationTracker;

  // ----- Allocations (SSOT → code) -----

  allocation coreToWheel : SoftwareAllocate {
    end logical ::> memNetSystem.core;
    end code ::> wheel.core;
  }
  allocation mcpToWheel : SoftwareAllocate {
    doc /* Fleet MemNet MCP = tip/ops module; not sysmledge. */
    end logical ::> memNetSystem.mcp;
    end code ::> wheel.mcp;
  }
  allocation fleetToWheel : SoftwareAllocate {
    doc /* One wheel, many hosts (droplet + devices). */
    end logical ::> opsFleet;
    end code ::> wheel;
  }
  allocation dropletServiceToCore : SoftwareAllocate {
    end logical ::> opsFleet.droplet.memnet.core;
    end code ::> wheel.core;
  }
  allocation dropletMcpToTip : SoftwareAllocate {
    end logical ::> opsFleet.droplet.memnet.mcp;
    end code ::> wheel.mcp;
  }
  allocation deviceServiceToCore : SoftwareAllocate {
    end logical ::> opsFleet.devices.service;
    end code ::> wheel.core;
  }

  allocation inProcessToMod : SoftwareAllocate {
    end logical ::> memNetSystem.core.transport.inProcess;
    end code ::> inProcessMod;
  }
  allocation ipcToMod : SoftwareAllocate {
    end logical ::> memNetSystem.core.transport.ipc;
    end code ::> ipcMod;
  }
  allocation tcpToMod : SoftwareAllocate {
    end logical ::> memNetSystem.core.transport.tcp;
    end code ::> tcpMod;
  }
  allocation tcpDaemonToMod : SoftwareAllocate {
    end logical ::> memNetSystem.core.transport.tcp;
    end code ::> serveDaemonMod;
  }
  allocation adminUsageToMod : SoftwareAllocate {
    end logical ::> memNetSystem.core.transport.tcp.adminUsage;
    end code ::> adminUsageMod;
  }
  allocation safeUpgradeToMod : SoftwareAllocate {
    doc /* Drain, manifest, startup restore (newest valid set, MN-REQ-06.17), and retire on memnet-serve. */
    end logical ::> memNetSystem.core.transport.tcp.safeUpgrade;
    end code ::> safeUpgradeMod;
  }
  allocation serveRetryToMod : SoftwareAllocate {
    doc /* Client pause through a serve restart or drain; never replays a write (MN-REQ-06.19). */
    end logical ::> memNetSystem.core.transport.tcp.clientRetry;
    end code ::> serveRetryMod;
  }
  allocation serveCheckpointToMod : SoftwareAllocate {
    doc /* Per-session checkpoint snaps on memnet-serve. Not agent MCP. */
    end logical ::> memNetSystem.core.transport.tcp.serveCheckpoint;
    end code ::> serveCheckpointMod;
  }
  allocation snapshotAclToMod : SoftwareAllocate {
    doc /* Session ACL in snapshot save / load (MN-REQ-06.16). */
    end logical ::> memNetSystem.core.transport.inProcess.memory.sessions.snap;
    end code ::> snapAclMod;
  }
  allocation cliToMod : SoftwareAllocate {
    end logical ::> memNetSystem.core.cli;
    end code ::> cliMod;
  }
  allocation sessionsToMod : SoftwareAllocate {
    end logical ::> memNetSystem.core.transport.inProcess.memory.sessions;
    end code ::> sessionsMod;
  }
  allocation storeToMod : SoftwareAllocate {
    end logical ::> memNetSystem.core.transport.inProcess.memory.sessions.store;
    end code ::> storeMod;
  }
  allocation memStoreToMod : SoftwareAllocate {
    end logical ::> memNetSystem.core.transport.inProcess.memory.sessions.store;
    end code ::> memStoreMod;
  }
  allocation capsToMod : SoftwareAllocate {
    end logical ::> memNetSystem.core.transport.inProcess.memory.sessions.caps;
    end code ::> capsMod;
  }
  allocation capsAclToMod : SoftwareAllocate {
    end logical ::> memNetSystem.core.transport.inProcess.memory.sessions.caps;
    end code ::> capsAclMod;
  }
  allocation gqlToMod : SoftwareAllocate {
    end logical ::> memNetSystem.core.transport.inProcess.memory.sessions.gqlWire;
    end code ::> gqlMod;
  }
  allocation parseFrontToMod : SoftwareAllocate {
    end logical ::> memNetSystem.core.transport.inProcess.memory.sessions.gqlWire.parseFront;
    end code ::> parseFrontMod;
  }
  allocation productGateToMod : SoftwareAllocate {
    end logical ::> memNetSystem.core.transport.inProcess.memory.sessions.gqlWire.productGate;
    end code ::> gqlPyMod;
  }
  allocation schemaToMod : SoftwareAllocate {
    end logical ::> memNetSystem.core.transport.inProcess.memory.sessions.schema;
    end code ::> schemaMod;
  }
  allocation snapToMod : SoftwareAllocate {
    end logical ::> memNetSystem.core.transport.inProcess.memory.sessions.snap;
    end code ::> snapMod;
  }
  allocation housekeepToMod : SoftwareAllocate {
    end logical ::> memNetSystem.core.transport.inProcess.memory.sessions.housekeep;
    end code ::> housekeepMod;
  }
  allocation mutateToMod : SoftwareAllocate {
    end logical ::> memNetSystem.core.transport.inProcess.memory.sessions.recallCommit.commit.mutate;
    end code ::> mutateMod;
  }
  allocation rsvToMod : SoftwareAllocate {
    end logical ::> memNetSystem.core.transport.inProcess.memory.sessions.recallCommit.commit.reserve;
    end code ::> rsvMod;
  }
  allocation sameThingToMod : SoftwareAllocate {
    end logical ::> memNetSystem.core.transport.inProcess.memory.sessions.recallCommit.commit.sameThing;
    end code ::> sameThingMod;
  }
  allocation pinMapToMod : SoftwareAllocate {
    end logical ::> memNetSystem.core.transport.inProcess.memory.sessions.recallCommit.recall.shapedRead.pinMap;
    end code ::> pinMapMod;
  }
  allocation findToMod : SoftwareAllocate {
    end logical ::> memNetSystem.core.transport.inProcess.memory.sessions.recallCommit.recall.shapedRead.find;
    end code ::> pinMapMod;
  }
  allocation peakLToMod : SoftwareAllocate {
    end logical ::> memNetSystem.core.transport.inProcess.memory.sessions.recallCommit.recall.seed.peak;
    end code ::> peakLMod;
  }
  allocation absorbToMod : SoftwareAllocate {
    end logical ::> memNetSystem.multitask.coordinator.importReceive.absorb;
    end code ::> absorbMod;
  }
  allocation cheapLlmToMod : SoftwareAllocate {
    end logical ::> memNetSystem.multitask.coordinator.importReceive.guard.cheapLlm;
    end code ::> cheapLlmMod;
  }
  allocation ingestToMod : SoftwareAllocate {
    end logical ::> memNetSystem.pinMaps;
    end code ::> ingestMod;
  }
  allocation exportToMod : SoftwareAllocate {
    end logical ::> memNetSystem.pinMaps.export;
    end code ::> exportMod;
  }
  allocation catalogToMod : SoftwareAllocate {
    end logical ::> memNetSystem.pinMaps.catalog;
    end code ::> catalogMod;
  }
  allocation agensToMod : SoftwareAllocate {
    end logical ::> memNetSystem.durable.agens;
    end code ::> agensMod;
  }
  allocation ragHookToMod : SoftwareAllocate {
    end logical ::> hostSearch.hook;
    end code ::> ragHookMod;
  }
  allocation mcpToolsToMod : SoftwareAllocate {
    end logical ::> memNetSystem.mcp.tools;
    end code ::> mcpFacadeMod;
  }
  allocation mcpToolsToServer : SoftwareAllocate {
    end logical ::> memNetSystem.mcp.tools;
    end code ::> wheel.mcp;
  }
  allocation mcpBridgeToMod : SoftwareAllocate {
    end logical ::> memNetSystem.mcp.bridge;
    end code ::> mcpBridgeMod;
  }
  allocation mcpHttpToMod : SoftwareAllocate {
    doc /* Streamable-http sibling of ServeBridge; Multitask shared store. */
    end logical ::> memNetSystem.multitask.sharedStore;
    end code ::> mcpHttpMod;
  }
  allocation lawSeedToMod : SoftwareAllocate {
    end logical ::> memNetSystem.mcp.seed;
    end code ::> lawSeedMod;
  }
  allocation productGatewayToMod : SoftwareAllocate {
    doc /* Shipped product gateway. Parent #191 catalogue stays invent-only. */
    end logical ::> lanMcpFront.productGateway;
    end code ::> productGatewayMod;
  }

  // CousinSysMLEdge has no SoftwareAllocate in this package.

  // ----- Atelier-board asks (PROPOSAL; MN-REQ-14; 14.1, 14.3, 14.4, 14.9-14.13 implemented, 14.2 PARKED) -----
  // 14.9 to 14.12 are shipped with runtime tests (SessionByteBudget in snapshot.py,
  // BypassPathCaps in bypass_caps.py, SessionByteLedger in session_bytes.py; config.py holds the caps).
  // 14.1 and 14.4 are implemented (tests/test_range_where.py, tests/test_id_opaque_range.py,
  // tests/test_id_index.py, tests/test_id_index_perf.py);
  // 14.3 is implemented (TypedWalk; tests/test_typed_walk.py, tests/test_typed_walk_where.py,
  // tests/test_walk_index.py, tests/test_typed_walk_perf.py);
  // 14.5-14.8 are PROPOSAL target only: no SoftwareAllocate, no CodeModule path.
  // 14.2 is PARKED.
  part def AtelierBoardAskPlan {
    doc /*
      Engine touch points for MN-REQ-14 (parts/common/memnet/memnet/;
      line numbers at the range-where-id-index combine; 14.3 at the
      typed-walks head). 14.1, 14.3, 14.4 and 14.9-14.12 are implemented
      and listed where they landed; the other
      items are where a later cut would land, and the tracker MUST NOT
      list those as implemented.
      14.1 range WHERE (implemented): parse gql.py:282-319 (range on id
           refused unsupported_predicate, gql.py:287-289), three-valued
           evaluation gql.py:321-399; relationship WHERE ... DELETE
           RelDropRec gql.py:132 and gql.py:1252, resolved in
           mutate_gate.py:996-1050.
      14.2 paged reads (PARKED): config.py:71 cap; gql_parse_front.py:34.
      14.3 typed directed walks (implemented; part TypedWalk): engine
           typed_walk.py:103-196, reply emit_walk :240-263; adjacency
           index in RecordTable mem_store.py:34-97, MemStore.typed_edges
           :609-617, verify_indexes adjacency check :689-699; order-exact
           rollback mutate_gate.py:608, :723-761; verb cli.py:1948-2000.
      14.4 id index and linear load (implemented): RecordTable
           mem_store.py:34-175 (high-water kept by clear(), :127-133),
           match_nickname :423, load_records :205-232; #@IDHW: line
           snapshot.py:393-438 and load :795, :842; find by id
           pin_map_composer.py:494-512.
      14.5 record cap: config.py:125, mem_store.py:267-272.
      14.6 id design (mint, tombstone, dup refusal): same index as 14.4.
      14.7 MCP surface: engine-side handle-to-id map; replies carry handles only.
      14.8 developer surface: separate listener/transport, own credential;
           replies carry real ids.
      14.9 value cap: config.py:130 (4,096 -> 32,768 bytes) and line cap
           config.py:131 (32,768 -> 135,168 = 4 x 32,768 + 4,096 bytes);
           mutate-time whole-line escaped-size line_bytes refusal; docs/cap-contract.md
           lines 153-158 change in the code PR (#238).
      14.10 per-session total-bytes cap (escaped snapshot line bytes): new knob
           MEMNET_MAX_SESSION_BYTES, default 163,840,000 (escaped
           snapshot line bytes); refusal limit_exceeded|session_bytes.
      14.11 bypass paths: bypass_caps.py (checkpoint, verify, rollback) used by
           import_absorb.py, durable/sync.py, cli.py delete and housekeep.py
           prune; snapshot.py refuse_session_budget (save) and
           refuse_snapshot_text_budget (load).
      14.12 incremental budget check: session_bytes.py (SessionBytes ledger,
           incremental_total, full_recount_total, check_budget) with a
           dirty journal on MemStore; wire.py join_payload via str.translate.
    */
    attribute implemented : Boolean = false;
    attribute parkedItems : String = "MN-REQ-14.2";
    attribute dependsOn : String = "MN-REQ-14.5 after MN-REQ-14.4";
    // No satisfy: implemented=false must not look done to a tracker.
  }

  // ----- Atelier-board target structure (PROPOSAL 14.5-14.8; MN-REQ-14) -----
  // Target design only: implemented=false, no SoftwareAllocate, no CodeModule
  // path, no satisfy. Each part traces to its MN-REQ-14 leaves by a plain
  // dependency targetTrace_<Part>_<Req>, which the tracker does not count.
  // Exception: IdIndex is implemented for 14.4 and satisfies it; its 14.6
  // part stays a target trace. TypedWalk is implemented for 14.3 and
  // satisfies it.

  part def IdIndex {
    doc /*
      Implemented (MN-REQ-14.4; RecordTable, mem_store.py:34, is
      MemStore._by_hid; tests tests/test_id_index.py,
      tests/test_id_index_perf.py). In-memory index by nickname
      fields['id'] to hid, kept on every dict mutator (rollback included;
      reindex(hid) after an in-place edit; verify_indexes() checks it);
      duplicate nicknames stay allowed (B-D2), so one nickname may map to
      several hids, in first-insert order. Rebuilt on load, never stored;
      reads return the same rows in the same order. Equality lookup only:
      an id is opaque identity, with no meaning from its value, order or
      sequence, and a range WHERE on id is refused (MN-REQ-14.1). Minted
      ids are unique among live rows and never minted again, even after a
      delete or a refused batch; for that only, RecordTable keeps a
      per-prefix high-water that is never lowered, clear() included
      (mem_store.py:127-133). It persists through the snapshot "#@IDHW:"
      line only (snapshot.py:393-438); durable / agensgraph does not
      carry it yet. Still target (MN-REQ-14.6): a real-id key, UUIDv7
      minting, tombstones and refusal of a duplicate or tombstoned id.
    */
    attribute implemented : Boolean = true;

    satisfy MN_REQ_00_MissionBridge::MN_REQ_14_AtelierBoardAsks::MN_REQ_14_4_IdIndexAndLinearLoad;
  }
  dependency targetTrace_IdIndex_14_6
    from IdIndex
    to MN_REQ_00_MissionBridge::MN_REQ_14_AtelierBoardAsks::MN_REQ_14_6_IdDesign {
    doc /* PROPOSAL target trace; not a satisfy; tracker does not count it. */
  }

  part def TypedWalk {
    doc /*
      Implemented (MN-REQ-14.3; behaviour TypedWalk; verify MN-VER-14-S03;
      tests tests/test_typed_walk.py, tests/test_typed_walk_where.py,
      tests/test_walk_index.py, tests/test_typed_walk_perf.py). Line refs
      at the typed-walks head, parts/common/memnet/memnet/. Engine module
      typed_walk.py (typed_walk :103-196, emit_walk :240-263; bounds
      WALK_MAX_HOPS 10, WALK_MAX_LIMIT 500, WALK_MAX_EXAMINED 20,000,
      WALK_MAX_REPLY_BYTES 1,048,576 at :28-33). Adjacency index (node
      hid, standard relation, out | in) -> edge hids inside the mem_store
      RecordTable (mem_store.py:34-97, MemStore._by_hid), read by
      MemStore.typed_edges (:609-617) in edge first-insert order, kept on
      every dict mutator and by _index_edge reindex (:781-790), checked by
      verify_indexes() (:689-699), never stored, rebuilt on load. The
      mutate_gate rollback of a refused batch is order-exact (delete
      journal mutate_gate.py:608; undo :723-761; MemStore.restore_row /
      finish_restore mem_store.py:450-499). Read verb cli.py query
      typed-walk (:1948-2000), read ACL as pin_map. No MCP tool (waits for
      14.7 handles); agent RETURN stays product-gated.
    */
    attribute implemented : Boolean = true;

    perform action walk : MemNetBehaviour::TypedWalk;

    satisfy MN_REQ_00_MissionBridge::MN_REQ_14_AtelierBoardAsks::MN_REQ_14_3_TypedDirectedWalks;
  }

  part def TombstoneStore {
    doc /*
      PROPOSAL (MN-REQ-14.6 / 14.10). Id-only entries (id + deleted marker)
      in the index and the snapshot; a legacy snapshot loads with an empty
      set. Not counted against the record cap; counted toward the
      per-session byte budget.
    */
    attribute implemented : Boolean = false;
  }
  dependency targetTrace_TombstoneStore_14_6
    from TombstoneStore
    to MN_REQ_00_MissionBridge::MN_REQ_14_AtelierBoardAsks::MN_REQ_14_6_IdDesign {
    doc /* PROPOSAL target trace; not a satisfy; tracker does not count it. */
  }

  part def HandleTable {
    doc /*
      PROPOSAL (MN-REQ-14.7). Engine-side map handle -> real id for the
      LLM-facing MCP surface. Handles are process-unique (never reused
      within the process) or carry their session; persisted in the
      session's snapshot, valid across evict/restore/save/load. A bad,
      stale or deleted handle is refused, and a foreign handle (minted in
      another session) is refused, never resolved to another record.
    */
    attribute implemented : Boolean = false;
  }
  dependency targetTrace_HandleTable_14_7
    from HandleTable
    to MN_REQ_00_MissionBridge::MN_REQ_14_AtelierBoardAsks::MN_REQ_14_7_AgentHandlesNotIds {
    doc /* PROPOSAL target trace; not a satisfy; tracker does not count it. */
  }

  port def DeveloperCredentialPort {
    doc /*
      PROPOSAL (MN-REQ-14.8). Credential check for the developer surface,
      its own credential, separate from the MCP credential. The MCP
      credential is refused here.
    */
    in item credential : String;
  }

  part def DeveloperListener {
    doc /*
      PROPOSAL (MN-REQ-14.8). Separate listener/transport for tool
      integration (never a flag on the MCP endpoint); replies carry stable
      real ids. A caller without the developer credential is refused.
    */
    attribute implemented : Boolean = false;
    port credentialIn : DeveloperCredentialPort;
  }
  dependency targetTrace_DeveloperListener_14_8
    from DeveloperListener
    to MN_REQ_00_MissionBridge::MN_REQ_14_AtelierBoardAsks::MN_REQ_14_8_DeveloperSurfaceRealIds {
    doc /* PROPOSAL target trace; not a satisfy; tracker does not count it. */
  }

  part def SessionByteBudget {
    doc /*
      Implemented (MN-REQ-14.10; engine enforcement in snapshot.py). Per-session total of
      escaped snapshot line bytes; set by env var MEMNET_MAX_SESSION_BYTES (maxSessionBytes);
      default 163,840,000 bytes (config.py DEFAULT_MAX_SESSION_BYTES; counted as escaped snapshot line bytes); an
      over-budget write, load, save, import or hydrate is
      refused limit_exceeded|session_bytes and stores nothing.
      The total is kept incrementally by SessionByteLedger (MN-REQ-14.12).
    */
    attribute implemented : Boolean = true;
    attribute maxSessionBytes : Integer = 163840000;

    satisfy MN_REQ_00_MissionBridge::MN_REQ_14_AtelierBoardAsks::MN_REQ_14_10_SessionTotalBytesCap;
  }

  part def BypassPathCaps {
    doc /*
      Implemented (MN-REQ-14.11; bypass_caps.py). Value, whole-line and
      session-byte caps on snapshot import, durable hydrate and CLI
      delete/prune, atomic: a refusal restores the store, relations and
      indexes. Deletes skip the byte budget but keep the line cap.
    */
    attribute implemented : Boolean = true;

    satisfy MN_REQ_00_MissionBridge::MN_REQ_14_AtelierBoardAsks::MN_REQ_14_11_BypassPathCaps;
  }

  part def SessionByteLedger {
    doc /*
      Implemented (MN-REQ-14.12; memnet/session_bytes.py: SessionBytes,
      incremental_total, full_recount_total, check_budget; dirty journal on
      MemStore). Per-session running sum of escaped UTF-8 line bytes,
      updated on create, update, delete, import, hydrate and load; a write
      re-encodes the changed nodes plus the incident edges of changed
      nodes. The
      total equals full_recount_total at every point
      (MEMNET_DEBUG_SESSION_BYTES=1 asserts it). A bypass_guard rollback or
      a failure inside the sync invalidates the ledger; the next check
      rebuilds it from the store.
    */
    attribute implemented : Boolean = true;

    satisfy MN_REQ_00_MissionBridge::MN_REQ_14_AtelierBoardAsks::MN_REQ_14_12_IncrementalByteBudget;
  }

  part def PagingCursor {
    doc /*
      Implemented (MN-REQ-14.13; behaviour PagedRead; verify MN-VER-14-S13;
      tests/test_paging_cursor.py). Engine module memnet/paging.py
      (fingerprint, encode_cursor, decode_cursor); typed_walk.typed_walk
      cursor / paged / session_id and WalkResult cursor, offset, cursor_at;
      pin_map_composer.bounded_match_find offset; read verbs cli.py query
      find (--cursor, --paged) and query typed-walk (--cursor, --limit);
      memnet_mcp.server find (cursor, paged) and typed_walk (limit, cursor,
      next_cursor). Stateless on the server: the token holds the position,
      so it survives evict and restore only while MemStore.change_count is
      unchanged (otherwise stale_cursor).
    */
    attribute implemented : Boolean = true;

    perform action page : MemNetBehaviour::PagedRead;

    satisfy MN_REQ_00_MissionBridge::MN_REQ_14_AtelierBoardAsks::MN_REQ_14_13_PagingCursor;
  }

  part def AtelierBoardTargetEngine {
    doc /*
      PROPOSAL (MN-REQ-14; target only). Composes the MN-REQ-14 target
      parts and wires the behaviour: range WHERE (14.1), cap enforcement on
      write and load at line cap 135,168 (14.9 / 14.10), the D02 WHERE+SET
      fix (implemented; MN-VER-14-D02 fixed), the id lifecycle (14.6) and the session byte budget
      (14.10) and the typed walk (14.3, implemented; part TypedWalk). 14.2
      paging stays PARKED and is not composed here.
    */
    attribute implemented : Boolean = false;
    part idIndex : IdIndex;
    part tombstones : TombstoneStore;
    part handles : HandleTable;
    part developer : DeveloperListener;
    part byteBudget : SessionByteBudget;
    part bypassCaps : BypassPathCaps;
    part typedWalk : TypedWalk;

    perform action rangeWhere : MemNetBehaviour::RangeWhereCompare;
    perform action capEnforce : MemNetBehaviour::ValueLineCapEnforce;
    perform action bypassCapEnforce : MemNetBehaviour::BypassPathCapEnforce;
    perform action whereSetFix : MemNetBehaviour::WhereSetRefusalFix;
    perform action idMint : MemNetBehaviour::IdMintAndRetire;
    perform action handleResolve : MemNetBehaviour::HandleResolve;
    perform action developerLookup : MemNetBehaviour::DeveloperIdLookup;
    perform action boardWake : MemNetBehaviour::BoardWakeRead;
    perform action loadLinear : MemNetBehaviour::SessionLoadLinear;
    perform action typedWalkRead : MemNetBehaviour::TypedWalk;
    exhibit state idLifecycle : MemNetBehaviour::IdLifecycle;
    exhibit state byteBudgetStates : MemNetBehaviour::SessionByteBudgetStates;
  }
}
