/*
  MemNet requirements -- nested + atomic baseline (2026-07).

  ID scheme:
    MN-REQ-00          mission root (sole parent)
    MN-REQ-NN          group requirement (organisational; short framing doc)
    MN-REQ-NN.M        atomic leaf (one SHALL/SHOULD idea)
    MN-REQ-10          LLM assumed properties + limitation leaves
    MN-REQ-11          Snapshot / interoperability (map of pins)
    MN-REQ-12          Multitask Mode (parent/worker; shared session as-is)
    MN-REQ-13          0.5 Recall/Commit (thin; math skeleton; no engine cut)
    MN-REQ-13.2        SameThingAbsorb — in-session Commit rule (not ImportAbsorb)
    MN-REQ-02.8        GraphElement identity; optional nickname; leftover mint/store-key
    MN-REQ-02.9        MUST NOT copy cousin store-key / unique-name / embedding Recall
    MN-REQ-04.8        Cue |Q|>1 stays RelativeSeed bounded + honest; CueConflict
                       on find/pin_map emit; same name is a candidate only
    MN-REQ-04.9        Empty-q session outline: Recall census of S (kinds +
                       LIMIT exemplars); leftover empty-seed skip not TARGET
    MN-REQ-04.10       Peak_L last-resort residual cue on codebook miss;
                       never default goldfish
    MN-REQ-04.11       pin_map order is a function of Shape observables,
                       not hid / nickname id / CREATE order (gauge)
    MN-REQ-04.12       Housekeep orphan/dangling/stale resolve edge ends by
                       hid and nickname; prune --apply refuses a referenced node
    MN-REQ-06.5        Human usage look (read-only dashboard; not agent wire)
    MN-REQ-06.6        Device MemNet services; one MemNet MCP (tip/ops) at the droplet; product face is sysmledge (tip≠face)
    MN-REQ-06.7        Allocate SSOT parts to live code in this checkout (one Hatch wheel, many hosts; sysmledge not in wheel)
    MN-REQ-06.8        Tip MemNet access portal (ops): admin invite, Google login, Bearer for keyed tip MCP; tip≠face
    MN-REQ-06.9        LAN MCP front invent (#191): ClusterRoute — where the session lives; one MCP catalogue, N LAN serves; cousin of #47; inventOnly
    MN-REQ-06.10       SliceHandCarry invent (#47 cousin): bounded WorkingMemorySlice copy into another session; not a live hop; inventOnly
    MN-REQ-01.9        Snapshot save/load lossless property round-trip; fail-closed save;
                       expire-save failure keeps RAM and counts against the session cap
    MN-REQ-01.10       CapsPolicy who-check on session save / load-into-ACL / close
    MN-REQ-03.4        MATCH WHERE SET/DELETE SHALL honour the predicate or refuse
    MN-REQ-05.3        One decoded value_bytes cap on pipe mutate, GQL mutate, snapshot load
    MN-REQ-05.4        One effective-field cap (default 64) on SCHEMA register, mutate, snapshot save/load; save never stricter than write
    MN-REQ-05.5        Session cap evicts least-recently-touched saveable session (shipped, unreleased); save victim first; none evictable refuses limit_exceeded ("all sessions are in use"); restore: same ACL, no lease carried over
    MN-REQ-06.11       Admin-only serve usage report (counts/caps; opaque session alias; not agent MCP)
    MN-REQ-06.12       Product gateway on memnet-mcp: per-product route to owning serve (not mn_tip_)
    MN-REQ-06.13       Serve request isolation: each command's stdout, stderr, and exit_code
    MN-REQ-06.14       Safe serve upgrade inside memnet serve: drain, manifest, restore, retire (audit mark; a later restart still restores, 06.17); no silent session loss
    MN-REQ-06.15       Admin checkpoint of every loaded session: lossless snaps, no drain, no traffic refuse
    MN-REQ-06.16       Session snapshot carries the ACL (enabled, grants, digest-only bind); format 2 SHALL carry #@ACL:; format 1 loads ACL off (@ACL: absent|off); files 0600; first v2 write over v1 keeps <file>.v1.bak once (0600); no dual write
    MN-REQ-06.17       Restart restore from the newest valid snapshot set (checkpoint or upgrade-prepare); every restart restores; loud fallback (@WARN: restore_fallback); none valid exits 3 (implemented; tests/test_restart_restore.py)
    MN-REQ-06.18       memnet-mcp fails fast without the [mcp] extra: one stderr line mcp_extra_missing, exit 2 (implemented; tests/test_mcp_extra_missing.py)
    MN-REQ-06.19       Restart-safe transport: stateless memnet-mcp-http; ServePool/gateway pause through a serve restart or drain by bounded retry (30 s); a write is never replayed after send (implemented; tests/test_serve_restart_retry.py)
    MN-REQ-11.17       Catalog Snap / model Snap — session strata (0.15)
    MN-REQ-11.17.1     Cross-cut satisfy locators on the catalog; SysMLEdge
                       pin_map is a different tool (not this catalog)
    MN-REQ-11.17.2     Snap session grain is package / kind-band / nested
                       package; never one session per part or requirement
    MN-REQ-11.17.3     Snap budget pre-check; refuse named; mint all-or-nothing
    MN-REQ-11.17.4     Caller gone or wait exceeded: named refuse; rollback
    MN-REQ-11.17.5     Repeat Snap of the same model identity replaces, not doubles
    MN-REQ-14          Atelier-board engine asks (PROPOSAL, 2026-11-02; Atelier Keeper
                       benchmarks, synthetic, origin/master bb4a4dc); 14.1, 14.3, 14.4, 14.9-14.13 implemented; 14.2 PARKED; 14.5-14.8 PROPOSAL
    MN-REQ-14.1        WHERE range comparisons < > <= >= on SET / DELETE WHERE, never on id; a quoted number or a quoted string against a stored number is refused where_type_mismatch (implemented; tests/test_range_where.py, test_range_type_refusal.py)
    MN-REQ-14.2        Paged reads past the 50-row cap (PARKED: Elon review; since-filter note)
    MN-REQ-14.3        Typed directed walks: query typed-walk, one edge type, out/in/both, 1..10 hops (implemented; tests/test_typed_walk.py, test_walk_index.py)
    MN-REQ-14.4        Nickname id index and linear session load (implemented; tests/test_id_index.py, test_id_index_perf.py)
    MN-REQ-14.5        Session record cap raisable once 14.4 lands (depends on 14.4)
    MN-REQ-14.6        Id design: UUIDv7 minted, never reused, tombstoned (PROPOSAL; traced to 14.4)
    MN-REQ-14.7        MCP surface: handles only, never real ids (PROPOSAL; traced to 14.6)
    MN-REQ-14.8        Developer surface: real ids, stable outside references (PROPOSAL; traced to 14.6)
    MN-REQ-14.9        Value cap 4096 -> 32768 bytes and line cap 135168, no chunking (implemented; tests/test_value_cap_32k.py, test_line_cap_whole_line.py, test_line_cap_edge_schema.py)
    MN-REQ-14.10       Per-session total-bytes cap: escaped snapshot line bytes (default 163,840,000 bytes)
    MN-REQ-14.11       Write paths that bypass the mutate gate enforce the same caps (import, hydrate, CLI delete/prune; load and save budget)
    MN-REQ-14.12       Budget check is incremental: re-encodes changed nodes + their incident edges, total equal to a full recount (implemented; tests/test_session_bytes_incremental.py, test_join_payload_vectorised.py)
    MN-REQ-14.13       Opaque paging cursor for find and typed walks: limit + cursor in, next cursor out; bad_cursor / cursor_mismatch / stale_cursor; opt-in, replies unchanged otherwise (implemented; tests/test_paging_cursor.py)

  Nesting: requirement def inside requirement def only (SysML requirements
  tree). Deploy software elements satisfy leaves; they are not the
  requirement structure.

  Formal derivation (SysML v2 idiom for SysML 1.x deriveReqt):
    import RequirementDerivation::*; then
    #derivation connection {
      end #original ::> <parent usage>;
      end #derive ::> <child usage>;
    }
    Groups derive from MN-REQ-00; leaves derive from their group.
    Nesting = structure; #derivation = formal deriveReqt edge.

  Breaking rename: MN-R1...MN-R9 retired. Do not map old numbers 1:1.

  Etymology: MemNet = Net of Memory -- durable facts + relations, not a chat
  notepad and not the search corpus.

  Mission SSOT: Net of Memory between LLM pipelines and data searching; aids
  system, programme, software, firmware, hardware, and documentation
  development; save time and tokens; high factual accuracy; LLM-friendly
  grammar on stdio/MCP; canonical parser for human inspection. GQL/openCypher
  has no store key: GraphElement (node or edge) is the identity.
  CREATE () is legal. properties() MAY be empty. Later MATCH/MERGE =
  labels + properties; an edge is type + end elements. NicknameIdProperty
  id is optional -- not identity. HiddenStoreHandle (elementId-style)
  is not a property, not on the wire, not a business key. 0.9 leftover
  invented store: leftover_by_id / leftover_id_first / leftover_NEW_mint /
  leftover_MERGE_by_id / leftover_allocate_from_locator /
  leftover_ingestIsIdRule. SHALL NOT invent a replacement application
  store key. Grammar spelling/identity SSOT is docs/grammar/openCypher.bnf
  (official file, Apache-2.0; NOTICE-openCypher.md) -- not a MemNet-invented
  id law, not TCK compliance, not a second accept path.

  Current realisation notes (not eternal identity):
    Target agent wire is openCypher-shaped GQL (ADR-001); Write = display
    redefined as bounded shaped pin_map subgraph wrapping GQL.
    Layer / Tier A = leftover engine only (not product accept; M2
    retired MutateGate accept; leftover codecs memnet.tier_a / memnet.layer).
    Legacy @TAG pipe may still appear in old session files (import once).
    Store is in-memory Node|Edge property-graph records; process binding
    prefers in-process, then local IPC, TCP as fallback; fixed engine laws
    often LAW01-LAW05. Durable AgensGraph-class store planned M2.5 behind
    MemNet (not LLM-direct). Requirements state behavioural contracts;
    surface spellings may change if the boundary still meets the contract.

  Stakeholders (comment only -- no structural defs in this file):
    LLM pipelines; data-search steps; MCP host; human inspectors who verify
    what the memory net knows via parse-faithful inspect/render.

  Out of scope: novel-writer product and general application framework.
  Structure (software elements, ports, connections) lives in deploy.sysml,
  connections.sysml, and implementation.sysml (allocate).
*/
package MemNetRequirements {
  private import ScalarValues::*;
  private import RequirementDerivation::*;

  // --- Mission root (nested requirement tree only) ---

  requirement def MN_REQ_00_MissionBridge {
    doc /*
      SHALL provide a Net of Memory (MemNet): an in-memory working-memory
      network of facts and relations -- not a chat notepad and not the
      search corpus -- that sits between pipelines of LLM calls and data
      searching, aiding the LLM for system, programme, software, firmware,
      hardware, and documentation development, with the aims of saving
      wall-clock time and token usage while keeping high accuracy when
      presenting facts. The live graph is working memory. Durability is a
      file snapshot (explicit save and expire-save are one blob) or an
      optional cabinet ego slice. The session id is the mission handle.
      The model SSOT is git sysml-models/ on this repo and on
      modelbasedPrj-*. A bound SysMLEdge desk is the working model only
      on SysMLEdgePrj-*.
    */
    attribute requirementId : String = "MN-REQ-00";

    // ----- Session lifecycle -----

    requirement def MN_REQ_01_SessionLifecycle {
      doc /*
        Group: named session working memory across pipeline turns.
        The live graph is working memory. The session id is the mission
        handle, not the model SSOT. Durability is the file snapshot
        (explicit save and expire-save write one blob) or an optional
        cabinet ego slice.
      */
      attribute requirementId : String = "MN-REQ-01";

      requirement def MN_REQ_01_1_NamedSessions {
        doc /*
          SHALL provide named sessions that retain working-memory state across
          turns so pipeline facts outlive chat context.
        */
        attribute requirementId : String = "MN-REQ-01.1";
      }

      requirement def MN_REQ_01_2_SessionLifecycleOps {
        doc /*
          SHALL support open, resume, and close for each named session.
        */
        attribute requirementId : String = "MN-REQ-01.2";
      }

      requirement def MN_REQ_01_3_SessionTtlAndCaps {
        doc /*
          SHALL apply configurable session TTL and a cap on concurrent
          sessions. Sliding TTL: live access extends expires_at. After
          TTL the in-memory session SHALL drop, except when expire-save
          is on and the snapshot cannot be written: RAM SHALL stay
          (MN-REQ-01.9) and the session still counts against
          MEMNET_MAX_SESSIONS. Optional expire session_save is
          configurable (MEMNET_SAVE_ON_EXPIRE, default off): file
          snapshot MAY remain on disk until the user deletes it;
          session_load restores RAM. When save-on-expire is off, TTL
          drops RAM as before. SHALL NOT auto-flush Neo4j. Explicit
          session_save and this expire-save write one
          SessionSnapshotBlob.
        */
        attribute requirementId : String = "MN-REQ-01.3";
      }

      requirement def MN_REQ_01_4_SaveSessionSnapshot {
        doc /*
          SHALL persist a named session to one durable file snapshot so
          working-memory state can outlive the process (schema, records,
          relations). Explicit session_save and expire-save write that
          same blob. The file is not the cabinet and not the model SSOT.
        */
        attribute requirementId : String = "MN-REQ-01.4";
      }

      requirement def MN_REQ_01_5_LoadSessionSnapshot {
        doc /*
          SHALL restore a named session from a durable snapshot into an active
          working-memory session.
        */
        attribute requirementId : String = "MN-REQ-01.5";
      }

      requirement def MN_REQ_01_6_OptionalKeepSessionId {
        doc /*
          On load, SHALL allow the caller to optionally keep the session id
          from the snapshot (keep_id); otherwise assign a new id.
        */
        attribute requirementId : String = "MN-REQ-01.6";
      }

      requirement def MN_REQ_01_7_SessionAsSsotHandle {
        doc /*
          A named session MAY be the SSOT for a mission SOMETHING
          (MissionWorkingSet). When so, an LLM SHALL pass that SOMETHING by
          delivering the session id only (SessionHandoff; module A → B pipe).
          Peers SHALL re-pin_map; chat, MissionDock payloads, and HTTP bodies
          SHALL NOT be treated as SSOT (extends MN-REQ-10.1; Multitask
          MN-REQ-12.1). This SSOT is the mission working-set handle. It
          is not the model SSOT (git sysml-models/ on this repo and on
          modelbasedPrj-*; a bound SysMLEdge desk only on SysMLEdgePrj-*).
        */
        attribute requirementId : String = "MN-REQ-01.7";
      }

      requirement def MN_REQ_01_8_NoGraphDumpHandoff {
        doc /*
          Session handoff SHALL NOT carry a full graph dump (or mission SSOT
          prose blob) as the handoff payload. SessionHandoff carries sessionId
          and caller, plus optional missionId, lease, anchors, and writeScope.
          Chat, MissionDock, and HTTP bodies SHALL NOT carry the graph.
          Mutate still hits CapsPolicy (who / what / bind).
        */
        attribute requirementId : String = "MN-REQ-01.8";
      }

      requirement def MN_REQ_01_9_SnapshotLosslessRoundTrip {
        doc /*
          Anything the write path accepts SHALL session_save and
          session_load byte-for-byte as the same property values.
          That includes LF, CR, tab, VT, FF, file/group/record
          separators, NEL, line/paragraph separators, backslash,
          both quote kinds, dollar, braces, pipe, and CJK. Snapshot
          emit SHALL escape those losslessly; load SHALL decode them.
          Record split SHALL be LF-only (MUST NOT use
          str.splitlines(), which splits on CR/VT/FF/NEL/LS/PS
          before unescape). Mutate stdin, leftover pipe batches,
          and GQL statement breaks SHALL use that same LF-only
          split (optional trailing CR stripped). A raw VT, FF,
          FS, GS, RS, NEL, LS, or PS inside a value SHALL stay
          inside that value and SHALL NOT start another statement.
          Properties mutate stores that are absent from the live
          tag SCHEMA SHALL persist by widening the snapshot SCHEMA
          (GraphElement extras and Path-B locators such as qname),
          including when the CREATE label spelling differs in case
          from the SCHEMA tag. A live SCHEMA that omits the id
          column SHALL still save: the snapshot SCHEMA gains an
          id column and a minted nickname. Live session SCHEMA is
          unchanged until load. Fixed
          tags EDG/LAW SHALL NOT widen; extras there SHALL fail
          closed. A CREATE, SET, or MERGE that would make a tag's
          effective field set (declared SCHEMA fields, undeclared
          extras on any row of that tag, and the id column save
          appends) exceed max_fields SHALL refuse
          limit_exceeded|fields n/max and SHALL NOT write
          (MN-REQ-05.4). Mutate and snapshot save SHALL share one
          effective-field count so save is never stricter than a
          mutate that succeeded. Default max_fields is 64
          (MEMNET_MAX_FIELDS). Snapshot load SHALL refuse a SCHEMA
          over that cap with the same fields n/max code. Save SHALL
          fail closed (snapshot_unsaveable naming the row) as a
          backstop rather than write an unloadable file,
          including when extras would exceed max_fields or the
          escaped line exceeds line_bytes. Expire-save that cannot
          write (snapshot_unsaveable or any other save failure,
          such as an unwritable disk or directory) SHALL NOT write
          a file and SHALL NOT drop RAM. The session stays live,
          still counts against MEMNET_MAX_SESSIONS, and every sweep
          or access that retries expiry SHALL emit
          @WRN: expire_snapshot_failed|<code>. Access after TTL
          SHALL report the session overdue
          (session_expired|overdue) so the caller can fix and save,
          or close. An explicit session_save that succeeds, or an
          explicit session_close, ends that hold. When
          MEMNET_SAVE_ON_EXPIRE is off, TTL still drops RAM as
          MN-REQ-01.3. Snapshots written by 0.19.18 (pipe and
          backslash escapes only) SHALL still load.
        */
        attribute requirementId : String = "MN-REQ-01.9";
      }

      requirement def MN_REQ_01_10_SessionLifecycleAclWho {
        doc /*
          When session ACL is enabled, session_save, session_load into
          that ACL'd session, and session_close SHALL accept --caller /
          MEMNET_CALLER and enforce CapsPolicy who-check with the same
          codes as pin_map / mutate (acl_who, acl_denied, acl_forbidden).
          MCP SHALL pass caller through on those tools. Without ACL,
          behaviour is unchanged.
        */
        attribute requirementId : String = "MN-REQ-01.10";
      }
    }

    // ----- Memory net information model: GQL node, edge, property -----

    requirement def MN_REQ_02_MemoryNetGraph {
      doc /*
        Group: the Net of Memory is a GQL property graph whose three elements
        are node (ISO synonym vertex), edge (ISO synonym relationship), and
        property (ADR-001; gql-wire-profile). GraphElement is the identity
        (CREATE () legal; properties MAY be empty). Grammar has no store
        key. Labels name kinds; they are not a fourth element. MUST NOT
        invent PORT (or nested graph) as a graph-element kind — those facts
        live as property values. MUST NOT invent an application store key.
        Agent wire is openCypher-shaped GQL; primary read is shaped pin_map
        (not raw MATCH/RETURN tables). NicknameIdProperty is optional
        (MN-REQ-02.8), not identity. HiddenStoreHandle off-wire.
        Layer / Tier A are archived (not product accept); @TAG pipe
        remains import-once only.
      */
      attribute requirementId : String = "MN-REQ-02";

      requirement def MN_REQ_02_1_ExactlyNodeAndEdge {
        doc /*
          SHALL model the Net of Memory as a GQL property graph with three
          elements: node (vertex), edge (relationship), and property. Topology
          is node--edge--node; property values attach to nodes and to edges.
          The graph element is the identity. CREATE () is legal. properties()
          MAY be empty. GQL grammar has no store key. SHALL NOT add a fourth
          graph-element kind (PORT nodes, nested graphs, prose blobs) and
          SHALL NOT invent an application store key in place of the element.
        */
        attribute requirementId : String = "MN-REQ-02.1";
      }

      requirement def MN_REQ_02_2_NodesHoldAtomisedFacts {
        doc /*
          Nodes SHALL hold atomised facts as property values --
          one idea per property -- not free-form prose or merged
          multi-idea blobs.
        */
        attribute requirementId : String = "MN-REQ-02.2";
      }

      requirement def MN_REQ_02_3_EdgesAreFirstClass {
        doc /*
          Edges (relationships) SHALL be first-class links between nodes,
          not buried in node property values or narrative.
        */
        attribute requirementId : String = "MN-REQ-02.3";
      }

      requirement def MN_REQ_02_4_QueryOverNodeEdgeGraph {
        doc /*
          Pin map, walk, bounded MATCH find, and query SHALL operate over the
          node/edge graph (property values included). Recall SHALL seed from
          a cue or pattern (find); pin_map then walks a shape. An optional
          nickname id MAY seed pin_map when present -- SHALL NOT require
          --anchor as law. Bounded MATCH find (hard LIMIT; shaped subgraph
          emit) is the un-nicknamed seed (Recall seed = MATCH; leftover #73)
          -- still not unbounded raw MATCH/RETURN dumps as goldfish. Both
          seeds are one Recall operator (MN-REQ-13).
        */
        attribute requirementId : String = "MN-REQ-02.4";
      }

      requirement def MN_REQ_02_5_GrammarExpressesNodeAndEdge {
        doc /*
          Agent-facing grammar and I/O SHALL express node, edge, and property as
          openCypher-shaped GQL (labels, edge/relationship types, property maps).
          Spelling/identity SSOT is the vendored official BNF
          docs/grammar/openCypher.bnf (Apache-2.0; NOTICE-openCypher.md) -- not
          a MemNet-invented id law, not TCK compliance, not a second accept
          path. Write = display means shaped subgraph emit matches mutate family.
          Layer / Tier A SHALL NOT be accepted on the product mutate path.
        */
        attribute requirementId : String = "MN-REQ-02.5";
      }

      requirement def MN_REQ_02_6_ParserRecoversNodeAndEdge {
        doc /*
          The canonical parser SHALL recover node, edge, and property structure for
          human inspection. Grammar parse front is GraphGlot (official grammar);
          MemNet product gate is a separate part after parse.
        */
        attribute requirementId : String = "MN-REQ-02.6";
      }

      requirement def MN_REQ_02_7_SchemaValidatedIngest {
        doc /*
          SHALL validate ingest against the session schema and reject unknown
          or reserved surface kinds. Tags MAY realise node labels; GQL
          elements remain node (vertex), edge (relationship), and property.
          SCHEMA SHALL NOT put id first as a required field. 0.9 leftover
          tag_map id_first remains engine as-is, not TARGET.
        */
        attribute requirementId : String = "MN-REQ-02.7";
      }

          requirement def MN_REQ_02_8_IdNotRequiredOnWire {
        doc /*
          Headline: GraphElement is identity. CREATE () is legal.
          properties() MAY be empty. Later MATCH/MERGE looks up labels +
          properties; an edge is type + end elements. HiddenStoreHandle
          stays inside the store -- not a property, not on the wire, not
          a business key. Agent wire SHALL NOT require NicknameIdProperty.
          Create, find, and pin_map MAY omit it. When present, id is a
          nickname only -- not identity. SHALL NOT invent a replacement
          application store key (locator-as-PK, qname-as-PK, minted
          string-as-PK). Id-exists / not-found (MN-REQ-03.1 / 03.2)
          remain valid only when an optional nickname is present.
          0.9 leftover invented store (not TARGET SHALL): leftover_by_id,
          leftover_id_first, leftover_NEW_mint, leftover_MERGE_by_id,
          leftover_allocate_from_locator, leftover_ingestIsIdRule,
          pin_map require_anchor.
        */
        attribute requirementId : String = "MN-REQ-02.8";
      }

      requirement def MN_REQ_02_9_MustNotCopyCousinStoreKey {
        doc /*
          Cousin pointing contrast (not a product switch). SHALL keep
          GraphElement identity and TARGET cue → RelativeSeed → ShapeWalk
          → pin_map emit. MAY copy cue-without-store-key and neighbourhood
          emit. SHALL NOT copy: GQL engine; content-hash-of-entire-property-map
          as identity; SQLite-clone product job; unique-name MERGE as
          universal identity; silent LLM merge of same-name nodes into
          the store (Recall SHALL NOT collapse; SameThingAbsorb is an
          agent-gated Commit rule); vector/fulltext as pointing; elementId
          writeback; Unicode id-normalization; substring/IDF as identity;
          Leiden; Cypher export as the query API; type:path:name as agent
          language; Fuse+embeddings as TARGET; commit-the-JSON as the
          memory product; SiYuan minted block id; NL2GQL vid / id(n) on
          the query wire; Logseq unique :block/name as required identity
          law. GraphLite SHALL remain a cabinet/store cousin — SHALL NOT
          replace the MemNet session-memory product. Cousins confirm
          TARGET; they SHALL NOT force a store-key back onto the wire.
        */
        attribute requirementId : String = "MN-REQ-02.9";
      }
    }

    // ----- Strict mutate -----

    requirement def MN_REQ_03_StrictMutate {
      doc /*
        Group: explicit create vs replace; no silent upsert.
      */
      attribute requirementId : String = "MN-REQ-03";

      requirement def MN_REQ_03_1_AddFailsIfExists {
        doc /*
          When an optional nickname id is present on create, SHALL fail with
          an id-exists error if that nickname is already taken. SHALL NOT
          require id on create. TARGET create is CREATE () / CREATE
          (:Label {props}) without id; properties MAY be empty.
          leftover_NEW_mint / leftover_by_id is 0.9 as-is, not this
          contract.
        */
        attribute requirementId : String = "MN-REQ-03.1";
      }

      requirement def MN_REQ_03_2_UpdateFailsIfAbsent {
        doc /*
          When an optional nickname id is present on replace (update), SHALL
          fail with a not-found error if that nickname is absent. Ends MATCH
          by label + properties when no nickname. SHALL NOT treat missing id
          as not-found of identity.
        */
        attribute requirementId : String = "MN-REQ-03.2";
      }

      requirement def MN_REQ_03_3_NoSilentUpsert {
        doc /*
          Silent upsert SHALL NOT be offered.
        */
        attribute requirementId : String = "MN-REQ-03.3";
      }

      requirement def MN_REQ_03_4_HonourWherePredicate {
        doc /*
          MATCH ... WHERE ... SET and MATCH ... WHERE ... DELETE SHALL
          NOT ignore the WHERE predicate. If lowering cannot honour it,
          the whole statement SHALL refuse with unsupported_predicate
          naming that predicate, and SHALL apply nothing. Forms that
          work today SHALL remain: MATCH (n WHERE true)-[r {id}]->()
          DELETE r (edge delete); property-map equality in MATCH.
          Honoured WHERE forms (equality, CONTAINS, STARTS WITH,
          ENDS WITH, =~, IN, true/false, AND/OR/NOT of those) SHALL
          actually filter.
        */
        attribute requirementId : String = "MN-REQ-03.4";
      }
    }

    // ----- Slice economy (pin map / recycle / walk) -----

    requirement def MN_REQ_04_SliceEconomy {
      doc /*
        Group: bounded live pin map for LLM turns (not the whole net);
        hide recyclable rows; optional relation walk; bounded MATCH find
        as cue/pattern seed (MN-REQ-04.6; shipped seed-only). Dark session
        empty q is session outline (MN-REQ-04.9) — census of S, not a
        neighbourhood and not leftover skip. 0.5 names this family
        Recall(q) (MN-REQ-13); pin_map and leftover find are the same
        operator with different seed rules. Nickname id is optional.
        Engine fixed-law rows (often LAW01-LAW05) are a current
        realisation, not the contract identity. Legacy name "warm" = live
        pin map (deprecated alias).
      */
      attribute requirementId : String = "MN-REQ-04";

      requirement def MN_REQ_04_1_AnchoredPinMap {
        doc /*
          SHALL return a bounded live pin map for a cued request -- a shaped
          neighbourhood digest of pins -- not the full session or a raw
          search dump. Goldfish seeds from a cue or pattern (find); pin_map
          walks a shape. RelativeSeed MATCH_L yields walk-root elements Q;
          ShapeWalk walks from Q. A dark session with empty q is outline
          (MN-REQ-04.9), not this neighbourhood and not view=shell grain.
          Nickname id as pin_map anchor is optional when a nickname exists.
          SHALL NOT require --anchor as law. 0.9 leftover require_anchor /
          by_id is engine as-is, not TARGET.
        */
        attribute requirementId : String = "MN-REQ-04.1";
      }

      requirement def MN_REQ_04_2_RecycleHiddenFromPinMap {
        doc /*
          SHALL hide rows marked for settle or expire recycle from the live
          pin map.
        */
        attribute requirementId : String = "MN-REQ-04.2";
      }

      requirement def MN_REQ_04_3_PinMapDepthAndRowCaps {
        doc /*
          SHALL cap live pin map depth and row count.
        */
        attribute requirementId : String = "MN-REQ-04.3";
      }

      requirement def MN_REQ_04_4_EngineLawPrepend {
        doc /*
          SHALL prepend session engine-law rows to the live pin map when
          those rows are present in the store.
        */
        attribute requirementId : String = "MN-REQ-04.4";
      }

      requirement def MN_REQ_04_5_AnchoredWalk {
        doc /*
          Anchored walk hop lines over the NODE and EDGE graph SHOULD be
          available for relation enumeration without loading the whole graph.
        */
        attribute requirementId : String = "MN-REQ-04.5";
      }

      requirement def MN_REQ_04_6_BoundedMatchFind {
        doc /*
          When no nickname id is known, or when pin_map caps dropped a
          needed row, the agent surface SHOULD offer a bounded MATCH find:
          label and/or property/locator predicates with LIMIT required
          (hard); optional max_rows aligned with MN-REQ-04.3; emit the same
          shaped subgraph family as pin_map / mutate (MN-REQ-08.9).
          SHALL NOT: binding-table RETURN as primary emit; missing LIMIT;
          unbounded MATCH; variable-length path as default; teach full
          openCypher (WITH / UNWIND / CALL / subqueries / ORDER BY).
          Distinct from mutate MATCH … SET. Shipped as BoundedMatchFind
          (implemented=true; #73) — realizes RelativeSeed MATCH_L, not
          pin_map k-hop, not copy-id then --anchor.
        */
        attribute requirementId : String = "MN-REQ-04.6";
      }

      requirement def MN_REQ_04_7_RelativeSeedThenShapeWalk {
        doc /*
          Goldfish query SHALL be discrete codebook tokens (kind / primary
          label, properties including locators, keyword; optional nickname
          id only if already set) — not a store-key id, not elementId, not
          a prose/embedding sentence, not rag_query / cosine / ANN, not
          free MATCH RETURN. Recall SHALL seed by RelativeSeed MATCH_L on
          those tokens (hard LIMIT L) yielding seed set Q of graph elements
          (relative nodes). Empty token / empty q SHALL be session outline
          (MN-REQ-04.9): Recall of S as a census — not skip, not invent a
          node, not MATCH a leftover id / --anchor as seed. leftover 0.10
          empty-seed skip remains leftover_* (productCommand=false; not
          TARGET). ShapeWalk SHALL walk k hops from Q under one M (not
          M×|Q|), hide recycled, and emit a shaped subgraph. SHALL NOT
          require a store-key anchor. Peak_L is a last-resort residual
          cue on codebook miss (MN-REQ-04.10), not this MATCH_L mechanism
          and not default goldfish. leftover 0.9 require_anchor / by_id /
          copied-id is leftover, not TARGET law. BoundedMatchFind / CmdFind
          realize RelativeSeed; PinMapShapedRead / CmdPinMap realize
          ShapeWalk (and empty-q outline). Peak_L nests under RelativeSeed.
          Still ONE Recall operator (MN-REQ-13.1).
        */
        attribute requirementId : String = "MN-REQ-04.7";
      }

      requirement def MN_REQ_04_8_CueMultiRootHonest {
        doc /*
          Open hard part without a third operator: a codebook cue MAY hit
          several relative roots (|Q| > 1). RelativeSeed SHALL stay
          bounded (hard LIMIT L) and honest — emit Q as walk roots, do
          not invent a node, do not silently pick a store-key. ShapeWalk
          SHALL union k-hop under one M (not M×|Q|). SHALL NOT add a new
          verb, Peak_L default, or rag_query / ANN to resolve ambiguity.
          Re-cue with a tighter token is the product move. Same name (or
          any shared cue) is a candidate only — not a find hit that
          collapses, not silent MERGE-by-name, not an LLM merge inside
          Recall. RelativeSeed / find SHALL emit Q honestly when |Q| > 1
          and SHALL NOT absorb. The existing find / pin_map shaped emit
          SHALL point the conflict out: Q listed, cardinality visible,
          CueConflict mark (usual case: shared name property; any shared
          cue that yields several roots is the same signal). SHALL NOT
          silently pick one root. Two different world-things that share a
          name SHALL appear as conflict (two roots), not as one merged
          node. SHALL NOT add name_conflict / merge / absorb as a product
          command. SameThingAbsorb stays a Commit rule after the agent
          sees the conflict. Contrast nest CousinPointingContrast
          records this; Recall/Commit operatorCount stays 2.
        */
        attribute requirementId : String = "MN-REQ-04.8";
      }

      requirement def MN_REQ_04_9_SessionOutlineEmptyCue {
        doc /*
          Teach name = outline. A dark session SHALL join the handed
          session id and ask the session, not a node. Empty q SHALL be
          Recall of S: a census of kinds that exist plus a few real
          nodes of each, with their actual labels and properties, under
          one hard LIMIT (Neo4j Browser / db.labels / AGE ag_label style
          + LIMIT exemplars). SHALL NOT MATCH a node as the seed (no
          leftover id, no --anchor). SHALL NOT skip empty seed as TARGET
          (leftover_empty_seed_skip is leftover only). SHALL NOT dump
          edges, dump S, absorb on the outline, MATCH-all, RAG search,
          HostSearch, getAllPages, Pattern C precomputed tour, or
          Pattern D seeded RAG. view=shell SHALL NOT be the outline
          (that is grain on an already-seeded walk). Leftover ids are
          not the next law; after outline the agent picks one seen cue
          and pin_maps. Still ONE Recall operator. CueConflict applies
          if exemplars collide on a name cue (two roots stay two).
          SHALL NOT: third operator; required property id; elementId on
          the wire; invent a store key; SameThingAbsorb as this cut;
          revive Layer; restore the retired Neo4j cabinet.
        */
        attribute requirementId : String = "MN-REQ-04.9";
      }

      requirement def MN_REQ_04_10_PeakLLastResort {
        doc /*
          Peak_L is a cue under RelativeSeed, not a third operator.
          When seed MATCH_L is empty and q is a non-empty codebook token
          (kind / props / keyword present, no hit), Recall SHALL seed from
          the typed residual local max of ρ* inside one S (incident edges
          except hierarchical contains; hide recycled), then ShapeWalk as
          usual. Empty q SHALL remain session outline (MN-REQ-04.9) —
          Peak_L SHALL NOT hijack outline. Peak_L SHALL NOT be default
          goldfish (defaultGoldfish=false). SHALL NOT use raw contains-tree
          degree, density-peak cluster assignment, Leiden from peaks, or
          global top-k degree as goldfish. SHALL NOT be a nest fix.
          Two peaks / two roots SHALL CueConflict (MN-REQ-04.8); SHALL NOT
          absorb in Recall; SHALL NOT silent MERGE-by-name. Hidden handle
          stays off the wire. operatorCount stays 2.
        */
        attribute requirementId : String = "MN-REQ-04.10";
      }

      requirement def MN_REQ_04_11_PinMapOrderFromObservables {
        doc /*
          Gauge honesty (0.19.c; not a usage-method b, not 0.20, not 1.0).
          The emitted order of a live pin_map SHALL be a function of the
          Recall Shape's observables: kind (primary label) plus the
          remaining property payload. HiddenStoreHandle (Record.hid /
          _elN / elementId-style) SHALL NOT be a ranking key, SHALL NOT
          appear on the wire, and SHALL NOT decide BFS expansion, edge
          emit, MATCH_L seed order, outline exemplars, Peak_L tie-break,
          max_rows admission, fan-out clamp, or view=shell truncation.
          Optional NicknameIdProperty id SHALL NOT be a ranking key
          either — ranking by nickname is the same class of leak as
          ranking by hid. Name / slug / locators are cue tokens, not
          identity. CREATE order and physical write_order SHALL NOT
          decide pin_map sequence. Still ONE Recall operator
          (MN-REQ-13.1): Recall = pin_map, Commit = mutate. SHALL NOT
          add rag_query, leftover add as product, Layer dialect, a third
          operator, or raise M. Cue by codebook tokens (kind + locator
          slug), never leftover id as the rank key.
        */
        attribute requirementId : String = "MN-REQ-04.11";
      }

      requirement def MN_REQ_04_12_HousekeepEndpointIdentity {
        doc /*
          Housekeep orphan, dangling, and stale counts SHALL resolve
          each edge endpoint by hidden element id (_elN) and by the
          optional id nickname. A GQL edge stores _elN. Comparing that
          token only to the nickname SHALL NOT mark every node an
          orphan. A node is an orphan only when no edge names it.
          An edge is dangling only when an end does not resolve.
          prune orphans and prune stale with --apply SHALL recompute
          with that rule and SHALL refuse prune_referenced, deleting
          nothing, when a candidate node is still an edge endpoint.
          The stale_orphans warning SHALL NOT suggest prune while
          edges still name those nodes. No sweep, housekeep job, or
          MCP tool SHALL run prune --apply; only an explicit CLI
          --apply does.
        */
        attribute requirementId : String = "MN-REQ-04.12";
      }
    }

    // ----- Hard caps -----

    requirement def MN_REQ_05_HardCaps {
      doc /*
        Group: bounded resource use under misuse.
      */
      attribute requirementId : String = "MN-REQ-05";

      requirement def MN_REQ_05_1_StoreResourceCaps {
        doc /*
          SHALL enforce hard caps on rows, law rows, relations, tags, fields,
          and value/line/batch bytes so the store cannot grow unbounded.
        */
        attribute requirementId : String = "MN-REQ-05.1";
      }

      requirement def MN_REQ_05_2_QueryFanoutCaps {
        doc /*
          SHALL enforce hard caps on pin-map/walk depth and fanout so token
          cost stays bounded under misuse.
        */
        attribute requirementId : String = "MN-REQ-05.2";
      }

      requirement def MN_REQ_05_3_ConsistentValueByteCap {
        doc /*
          The field-value byte cap SHALL be one hard cap on leftover
          pipe mutate, GQL mutate, and snapshot load, measured as the
          UTF-8 byte length of the decoded (raw) property value.
          Knob MEMNET_MAX_VALUE_BYTES, default 32768. Over-cap SHALL refuse
          limit_exceeded|value_bytes n/max and SHALL NOT accept the
          write. line_bytes is the UTF-8 byte length of the
          escaped/raw leftover-pipe or snapshot line (backslash and
          pipe count twice). Save verify and load SHALL use the same
          check (MEMNET_MAX_LINE_BYTES, default 135168 (4 x 32768 + 4096,
          worst-case escaping)). A single
          field under value_bytes still fits default line_bytes;
          many fields whose escaped form exceeds line_bytes SHALL
          fail closed at save (snapshot_unsaveable wrapping
          line_bytes) rather than write a file load will refuse.
        */
        attribute requirementId : String = "MN-REQ-05.3";
      }

      requirement def MN_REQ_05_4_ConsistentFieldCap {
        doc /*
          The fields-per-tag cap SHALL be one hard cap on SCHEMA
          register, GQL mutate, leftover pipe mutate, and snapshot
          save/load. The effective count is declared SCHEMA fields
          plus undeclared extras stored on any row of that tag,
          plus the id column snapshot save appends when the live
          SCHEMA omitted it. Default 64. Knob MEMNET_MAX_FIELDS.
          Over-cap mutate SHALL refuse limit_exceeded|fields n/max
          and SHALL NOT accept the write. Save SHALL use the same
          count (one shared helper) so anything mutate accepts can
          save and reload. Snapshot load SHALL refuse a SCHEMA over
          the cap with that same fields n/max code.
          snapshot_unsaveable remains the fail-closed save backstop
          when RAM still exceeds the cap (MN-REQ-01.9). Verify:
          MN-VER-05-S02 (tests/test_field_cap.py).
        */
        attribute requirementId : String = "MN-REQ-05.4";
      }

      requirement def MN_REQ_05_5_SessionCapEvictLru {
        doc /*
          Shipped in the unreleased engine. Runtime checks:
          tests/test_session_evict.py (no xfail).

          State (checked at 0.19.25 source). Session-scoped CLI commands
          call _load_session, which calls ss.touch(). So the MCP reads
          pin_map, query_warm, find, query_walk, read_list, export_pin_map,
          housekeep_stats and session_current already touch today, and so do
          the CLI-only reads (session_resume calls ss.touch() itself). The
          in-process get_session() only extends the TTL and does NOT touch:
          a read through get_session() alone leaves modified_at unchanged
          today. That is the gap the touch rule below closes. session_list,
          serve_status and the admin commands do not touch. The saves
          session_save, expire-save, admin checkpoint and evict-save do not
          touch either (MAINTENANCE-SAVES below); a save is not a read surface.

          Cap. At session open or load, after purge_expired, when the count
          reaches MEMNET_MAX_SESSIONS (default 1024) the engine SHALL pick at
          most one victim. One cap lock SHALL cover the count, the victim pick
          and the slot reservation; the victim is marked evicting under that
          lock. The save then runs outside the cap lock, under the victim's
          session lock.

          Victim. The live, non-evicting session with the oldest last touch,
          ordered by (modified_at, touch_seq) and compared as parsed instants,
          not as strings. SessionMeta.modified_at is set by SessionStore.touch();
          touch_seq is the tie-break (see Tie order). Every non-admin caller
          read SHALL set SessionMeta.modified_at through SessionStore.touch().
          The caller read surfaces are the READ-SURFACES block below; the
          reads that are NOT touches are the NON-TOUCH-READS block below.
          Writes (mutate, add, update, import_slice, ingest_*) are touches.
          Load (session_load) is a touch with a fresh TTL. Saves SHALL NOT
          touch: session_save, expire-save, admin checkpoint and evict-save
          (the MAINTENANCE-SAVES block below) SHALL leave modified_at and
          touch_seq unchanged. Open stamps the first touch (modified_at =
          created_at) and takes a touch_seq, so a never-read session has a
          defined last touch.

          Tie order. touch_seq is a process-wide monotonic counter held on the
          registry entry (SessionEntry) and advanced at every touch and open.
          Build option: touchSeqMonotonic=true, touchSeqInSnapshot=false. The
          counter is not persisted: a session loaded from a snapshot gets a
          fresh touch_seq, because the load is a touch. Order by name then id
          is the fallback only if a build cannot hold the counter; this build
          can, so the fallback is not used.

          The READ-SURFACES, NON-TOUCH-READS and MAINTENANCE-SAVES lists cover
          the MCP tools and the CLI-only surfaces. READ-SURFACES is MCP read
          tools, CLI-only reads
          (session_resume, tagmap_show, relations_list, query_neighbors,
          query_path, query_context, query_typed_walk (14.3),
          housekeep_stale, housekeep_orphans,
          housekeep_dangling, housekeep_recyclable) and the in-process
          get_session. Every session-scoped CLI command in cli.py is a read,
          a non-touch read, a maintenance save, or a non-read; the sync test fails
          on any other.

          READ-SURFACES-BEGIN
          get_session
          pin_map
          query_warm
          find
          query_walk
          query_typed_walk
          typed_walk
          read_list
          export_pin_map
          housekeep_stats
          session_current
          session_resume
          tagmap_show
          relations_list
          query_neighbors
          query_path
          query_context
          housekeep_stale
          housekeep_orphans
          housekeep_dangling
          housekeep_recyclable
          READ-SURFACES-END

          NON-TOUCH-READS-BEGIN
          serve_status
          session_list
          admin_usage_report
          admin_checkpoint_verify
          NON-TOUCH-READS-END

          MAINTENANCE-SAVES-BEGIN
          session_save
          expire_save
          admin_checkpoint
          evict_save
          MAINTENANCE-SAVES-END
          A fresh open cannot be its own victim: its session is not in the
          registry until its slot is reserved under the cap lock, so the pick
          never sees it. A load of an evicted id is excluded from its own pick
          the same way. Only an open bind or live writes (its session lock held
          by an in-flight mutate or commit) exempt any other session. A reserve
          (RSV) lease alone does NOT exempt its session. Exempt sessions are
          never auto-dropped.

          Save first. The victim's session lock SHALL be held from pick
          through save, RAM drop and registry removal, then released. The
          victim keeps its slot until it is dropped: the open that picked it
          waits for that save and takes the slot only after the drop. Under
          that lock the victim SHALL be written to MEMNET_EXPIRE_SNAPSHOT_DIR
          (reused; written whether or not MEMNET_SAVE_ON_EXPIRE is on) as an
          atomic write: temp file in the same directory, fsync the file,
          rename over the final name, fsync the directory; mode 0600; @SNAP
          version 2 with the ACL. Only after a complete save SHALL the engine
          drop the victim from RAM, then remove its registry entry. A failed
          save keeps the victim live (EvError: evictSaving to active); the
          engine then tries the next-oldest candidate, or refuses with
          limit_exceeded if none is left.

          Crash safety. A crash after the fsync and before the drop SHALL
          leave a complete snapshot. On restart the session is restored from
          that snapshot or is absent; never torn. Crash safety holds only where
          the filesystem supports directory fsync: EINVAL, ENOTSUP and
          EOPNOTSUPP from that fsync are tolerated, so there the rename is not
          guaranteed durable.

          No snapshot dir. MEMNET_EXPIRE_SNAPSHOT_DIR has no default. Without
          it the cap refuses and nothing is evicted. With it set, a full cap
          evicts. An optional neutral alias MEMNET_SNAPSHOT_DIR MAY name the
          same directory. If both are set to different paths, serve SHALL
          refuse to start: Caps construction fails with config_conflict and
          neither path is printed. The same path under both names is accepted.
          Dropping a separate eviction knob is deliberate: one dir, one meaning.

          Expiry never blocks reads; CLI and MCP reads of a session another thread holds wait for that holder; in-process get_session takes no lock and does not wait.

          Unsaveable. An unsaveable candidate (snapshot_unsaveable, over cap,
          or write error) SHALL stay live and the engine SHALL try the
          next-oldest candidate. No auto-drop of unsaveable sessions. The
          count of sessions held unsaveable SHALL be reported as
          sessions_unsaveable_held on serve_status and surfaced to admin.

          Refusal. If no session is evictable, the engine SHALL refuse with
          code limit_exceeded and the plain message "all sessions are in use".
          Nothing SHALL be dropped and no snapshot written.

          Restore. session_load of an evicted id from its snapshot SHALL give
          the same ACL, no lease carried over: reserve leases do not survive
          and the restored session has no bind. A load is a touch and starts
          a fresh TTL. The reopened session returns restored=true and emits
          no alerts.

          Lost lease. A commit naming a lease the caller no longer holds SHALL
          be refused with code lease_lost; nothing is written; the refused
          commit is not a touch. The commit names the held reserve with the
          new wire arg rid (MCP mutate rid=, CLI mutate --rid), and llm_id
          names the holder. lease= is not this arg: it stays the SessionBind
          lease (MN-REQ-06.16). The arg is new and shipped
          (deploy commitRefusesLostLease=true).

          A rid naming a live lease held by a different llm_id SHALL be refused
          with the existing code reserved (MutateGate reserve check,
          check_mutate_ids). reserve_conflict is the acquire-side overlap code
          and is not used on commit. Not lease_lost: the lease is still live.

          A commit that names no rid SHALL behave exactly as today: the
          MN-REQ-12.13 reserve check is unchanged (no_llm_id or reserved on a
          leased row). lease_lost fires only when a rid is named, so a no-rid
          commit after eviction and reload succeeds and changes the field.
          Regression, not xfail: tests/test_mutate_no_rid_regression.py.

          Caller. The caller result carries no cap and no eviction field: the
          caller is not told that a cap or an eviction exists. The open and
          load success results (CLI and MCP) carry no key matching cap, limit,
          max_sessions, sessions_count or evict. The evicted session's name or
          tag (never an mn_ id) and the sessions_evicted counter are reported
          on admin serve_status only. Accepted: the limit_exceeded refusal
          itself reveals that a cap exists. That refusal is the one
          caller-visible signal and is not hidden.

          Settled (not open): a lease does not survive eviction; a load is a
          touch with a fresh TTL; non-touch reads and saves are not
          touches; no default snapshot dir (no dir means the cap refuses;
          MEMNET_EXPIRE_SNAPSHOT_DIR is reused, with MEMNET_SNAPSHOT_DIR as an
          alias that must agree); one cap lock for count, pick and slot
          reservation; save outside the cap lock, under the victim lock; the
          victim keeps its slot until dropped and the picking open waits for
          its save; no auto-drop of unsaveable sessions, counted and surfaced.

          Ship (one commit, PR-facing). The commit that ships the engine SHALL
          in one change: (1) flip the module pytestmark in
          tests/test_session_evict.py to strict=True or drop the xfail, and drop
          the get_session and test_open_stamps_first_touch xfail marks in
          tests/test_read_touch_regression.py; (2) set
          deploy CapsPolicy evictShipped=true and commitRefusesLostLease=true;
          (3) add the deploy satisfy link
          MN_REQ_00_MissionBridge::MN_REQ_05_HardCaps::MN_REQ_05_5_SessionCapEvictLru;
          (4) flip the status guards caps.evictShipped == true in
          MN-VER-05-S03..S09 and caps.commitRefusesLostLease == true in
          MN-VER-05-S09. tests/test_sysml_session_evict.py::test_ship_flags_flip_together
          enforces (1) to (4): it fails unless evictShipped, commitRefusesLostLease,
          the satisfy link and the xfail marks all agree, and every guard matches.

          LATER (not dropped, not modelled): a "touched within the last N
          minutes" exemption. Do not add it until a measured run shows
          reload-thrash at cap=3: cycle opens over 4 or more live sessions and
          count evict-then-reload inside a short interval.

          LATER (not dropped, not modelled): "require rid on leased rows" (a
          no-rid commit on a leased row refused). Not a rule; add only if a
          measured run shows a lost-holder write slipping past the reserve check.

          Open items (doc only, not rules yet): (a) a distinct session_evicted
          refusal for a caller who holds an evicted id; (b) whether
          session_load of an evicted id returns the same id.

          Verify: runtime tests in tests/test_session_evict.py, cited by
          MN-VER-05-S03 to MN-VER-05-S09. Regression for the no-rid rule: tests/test_mutate_no_rid_regression.py.
        */
        attribute requirementId : String = "MN-REQ-05.5";
      }
    }

    // ----- Process / transport boundary -----

    requirement def MN_REQ_06_ProcessBoundary {
      doc /*
        Group: how clients bind to GraphStore and the session registry.
        Locked preference: in-process primary, local IPC for multi-process
        share, TCP localhost only as migration / fallback (not the core).
      */
      attribute requirementId : String = "MN-REQ-06";

      requirement def MN_REQ_06_1_InProcessPrimary {
        doc /*
          SHALL provide in-process GraphStore and session APIs as the primary
          binding for MCP and library users (lowest latency; no network hop).
        */
        attribute requirementId : String = "MN-REQ-06.1";
      }

      requirement def MN_REQ_06_2_LocalIpcShare {
        doc /*
          SHALL support a local IPC gateway when CLI and MCP must share one
          session registry across processes (prefer named pipe on Windows /
          AF_UNIX on POSIX).
        */
        attribute requirementId : String = "MN-REQ-06.2";
      }

      requirement def MN_REQ_06_3_TcpServeMigration {
        doc /*
          MAY expose TCP localhost length-prefixed serve as a migration or
          multi-process fallback; it SHALL NOT be treated as the conceptual
          core binding.
        */
        attribute requirementId : String = "MN-REQ-06.3";
      }

      requirement def MN_REQ_06_4_DurableStoreBehindMemNet {
        doc /*
          When a durable online GQL store (AgensGraph-class) is present,
          MemNet SHALL remain the sole agent-facing shared memory. The
          store SHALL sit behind MemNet (hydrate/flush). LLM ↔ store
          direct (Bolt / driver) SHALL NOT be the default teach path.
          M2.5 client hydrate/flush adapter seam IS landed (Fake always;
          optional AgensGraph client with liveCabinetClaimed; one
          DurableSyncOwner). Factory binds exactly one of fake or
          AgensGraph (bindsExactlyOneOf="fake|agensgraph").
          hydrateFlushCallers="tests" on DurableBuffer: no non-test
          caller of hydrate/flush. serve, IPC, and MCP bind the owner
          at startup and SHALL NOT be read as invoking it. SHALL NOT
          wire a new hydrate/flush caller. The 0.7 claim is adapter +
          operator round trip (no runtime caller). liveCabinetClaimed
          records that operator round trip. The AgensGraph server SHALL
          NOT be vendored in-repo. Neo4jAdapter, Neo4jLibraryPort, and
          liveNeo4jClaimed are retired on MemNetArchive (#187). When
          MEMNET_NEO4J_URL or any other MEMNET_NEO4J_* variable is set,
          the engine SHALL ignore it and start. One log warning is
          enough. SHALL NOT crash. SHALL NOT bind a Neo4j adapter.
          Hid SHALL stay off the wire. SHALL NOT fuse retrieve rankers
          (RRF / PPR / Leiden / ANN) into Recall / pin_map. HostSearch /
          RagHostHook SHALL remain outside MemNetSystem. Extra 0.17:
          RagHostHook.implemented SHALL be true outside MemNetSystem
          (skip is valid); SHALL NOT nest the hook under MemNetSystem;
          SHALL NOT add rag_query MCP. SHALL NOT read a Neo4j library.
        */
        attribute requirementId : String = "MN-REQ-06.4";
      }

      requirement def MN_REQ_06_5_HumanUsageLook {
        doc /*
          SHALL provide a read-only human look at live serve usage:
          serve_status (up / host / port), session census
          (@STAT sessions|n/max plus listed ids), housekeep_stats
          (caps / row counts), and optional ImportGuard armed display
          from env presence only. The look SHALL observe the serve
          registry / MultitaskSharedStoreBinding and SHALL NOT own
          SessionLifecycle. SHALL NOT expose session_close, mutate,
          import_slice, ImportGuard key entry, enable toggles that
          write, or reproject. SHALL NOT be agent wire, a second GQL
          API, or a Foam product MCP face (tip is not face). Manage of
          serve / MCP / roll / housekeep / ImportGuard env remains
          Memnetor + Devicor (CLI/MCP). HTTP/UI MAY stay parked
          (implemented=false) until Core GO. SemVer c only if later
          shipped without teaching agents the page as wire.
        */
        attribute requirementId : String = "MN-REQ-06.5";
      }

      requirement def MN_REQ_06_6_DeviceServicesOneDropletMcp {
        doc /*
          A droplet-centred ops fleet SHALL run MemNet engine/serve
          (MemNetCoreLibrary) on one or more device hosts (Pi,
          workstation, SBC) as separate services, each with its own
          session registry. The fleet SHALL instantiate at most one
          MemNet MCP (MemNetMcpServer) as the MemNet tip/ops engine
          face, and that MemNet MCP SHALL sit on the droplet host.
          That MemNet MCP is NOT the product invent face (tip≠face;
          tipIsFace=false). The product LLM face is the cousin
          SysMLEdge (`sysmledge` MCP on the droplet). MUST NOT invent
          upload/bind (mustNotInventUploadBind). Device hosts SHALL
          NOT nest a second product MCP and SHALL NOT nest
          SysMLEdge-as-product on the device. A tip MemNet MCP on a
          Pi for engine ops (memnet-mcp) is allowed and remains
          tip≠face (not sold as product). mcpNested=false means no
          product MCP nested, not a ban on ops tip. Product questions
          SHALL bind sysmledge only; MemNet tip/ops SHALL bind the
          droplet MemNet MCP and/or the Pi tip. MUST NOT answer
          product questions on the MemNet tip path. Each service
          keeps its own session handles (two handles stay two
          handles). This SHALL NOT be N-server federation (#47): no
          Cypher MERGE of live servers, no requirement that hosts
          share a cabinet, no mashed session ids. Handoff remains
          session id; optional Path-B import into a mission session
          stays ImportAbsorb, not a new pipe. Shared Multitask on
          one host still uses one serve (TCP / streamable-http)
          per MN-REQ-12.2.
        */
        attribute requirementId : String = "MN-REQ-06.6";
      }

      requirement def MN_REQ_06_7_SsotToCodeAllocate {
        doc /*
          SHALL allocate shipped logical SSOT parts (MemNetCoreLibrary,
          MemNetMcpServer, transport, session, RecallCommit, MCP, durable,
          pin-map, host-search) to live Python modules in this checkout
          via SoftwareAllocate (logical → code). One Hatch wheel
          (memnet-llm) SHALL instantiate on many hosts (droplet +
          devices); hosts are not extra packages (oneWheelManyHosts).
          The MemNet MCP module remains tip/ops (tipIsFace=false).
          Cousin SysMLEdge SHALL NOT be allocated here
          (sysmlEdgeInWheel=false; inThisRepo=false;
          mustNotInventUploadBind). The allocate package SHALL be
          the implementation tracker: each SoftwareAllocate row is a
          live path record (track=true; implemented=true iff the path
          exists in this checkout). Maintainers SHALL update the row
          when a module ships or moves; a missing path SHALL fail
          honesty tests. The derived map
          (sysml-models/outputs/ssot-to-code-allocate-map.md) SHALL
          list every row. Cousin sysmledge SHALL remain listed as
          not in this repo (sysmlEdgeTracked=false). MUST NOT invent
          upload/bind. MUST NOT be N-server federation (#47).
          Engine/MCP behaviour code SHALL NOT change solely to
          satisfy this allocate. Hatch stays 0.19.11 honesty c.
        */
        attribute requirementId : String = "MN-REQ-06.7";
      }

      requirement def MN_REQ_06_8_TipMemNetAccessPortal {
        doc /*
          SHALL provide an ops access portal for gated tip MemNet MCP
          keys. This portal is tip/ops access control (tip≠face). It
          SHALL NOT be the SysMLEdge product, a sysmledge key page, or
          an openProject gate. Admin SHALL be Szu-Wei and SHALL mint
          invite links for new users. An invited user SHALL redeem the
          invite onto an allowlist, then sign in with Google OAuth.
          After that login the portal SHALL issue and show that user's
          Bearer key for the tip MCP. Admin SHALL be able to revoke a
          key or an invite. The public tip endpoint
          https://memnet.139-59-255-181.nip.io/mcp SHALL require that
          Bearer (Authorization header) and SHALL forward only after
          auth to the Pi tip MemNet MCP. Unauthenticated MemNet MCP on
          that WWW URL SHALL be refused. Keyed tip MemNet on droplet
          WWW SHALL stay. This portal SHALL NOT grant open MemNet to
          strangers. Free use for strangers remains the SysMLEdge free
          tier or a self-hosted memnet-llm, not this portal. SHALL NOT
          change pin_map or engine operators. The portal web SHALL be
          the ops sidecar (portalWebImplemented=true; inventOnly=false).
          Google client secrets SHALL stay in the environment. nginx
          auth_request SHALL refuse unauthenticated /mcp. SHALL NOT
          sell this as invent_2_green (sellsInvent2Green=false).
          The portal web SHALL look at configured MemNet listeners
          and Bearer client last-used/use-count (statusLookOnly;
          serviceLookImplemented; clientLookImplemented). That look
          SHALL NOT unpark MemNetUsageDashboard HTTP
          (unparksUsageDashboard=false; dashboard httpImplemented
          stays false) and SHALL NOT restart, mutate, or
          session_close from the page.
        */
        attribute requirementId : String = "MN-REQ-06.8";
      }

      requirement def MN_REQ_06_9_LanMcpFrontSeveralServes {
        doc /*
          OPTIONAL Later invent (#191): named move ClusterRoute —
          where the session lives. One MemNet MCP front MAY
          catalogue sessions across several LAN memnet serve
          backends. Realised by MemNetLanMcpFront. This is
          engine/tip topology (tip≠face). SHALL NOT be the
          SysMLEdge product face, an AccountFace UI, or
          InvenTree. SHALL NOT nest under MemNetSystem.
          Distinct from MN-REQ-06.6 (one droplet MCP bound to that
          host's serve; device registries stay independent) and
          from MN-REQ-06.10 / #47 (SliceHandCarry: explicit copy
          of a bounded WorkingMemorySlice into another session;
          no shared catalogue; not a live hop).
          Placement: SessionOwnerRegistry entry SHALL be the owner
          of a session. Explicit pin of a new session to a live
          backend SHALL be allowed. Silent hash of sid SHALL NOT
          be the sole routing policy (hash MAY hint placement;
          owner is the registry row). session_open SHALL pin or
          pick a live backend, write the registry, and forward
          open to that serve. session_list SHALL union reachable
          backend catalogues, each row tagged with owner
          backendId, and SHALL NOT look complete if any backend
          clipped or was unreachable. session_current SHALL bind
          one sid owned by exactly one backend.
          One owner: each session lives on exactly one serve.
          SHALL NOT merge graphs across backends. Commit / mutate
          SHALL stay the owning serve's one gate.
          Recall: pin_map and find SHALL NOT span sessions on
          different backends in one call. Relocating where the
          SAME session lives MAY use SnapshotHandCarry
          (session_save then load, then update the registry).
          Copying atoms into a DIFFERENT session is SliceHandCarry
          (MN-REQ-06.10), not this cluster move.
          SHALL NOT invent shipped import_slice(from_url).
          Caps: hard max_rows / hops and truncation flags SHALL
          survive routing. A multi-backend answer SHALL NOT look
          complete if any backend clipped or was unreachable.
          Failure: serve_status SHALL be per-backend. Owner
          backend down SHALL fail loudly. Session relocate SHALL
          be optional save then load via snapshot dir, not silent
          migrate.
          TTL / expire-save: snapshot dir SHALL be per-backend by
          default. Shared NFS is an optional ops choice, not
          required by this model. Neo4j shared graph DB is
          retired (#189) and SHALL NOT be the cluster store.
          Auth: session ACL SHALL follow the session to its
          backend. LAN front↔backend SHALL require its own auth
          (not an open port). Unauthenticated MemNet MCP on the
          public internet SHALL stay refused (InkMirage CEO lock).
          Rate cap SHALL remain per-session; a per-backend cap
          MAY be an optional ops overlay.
          One serve already hosts many sessions. This invent
          SHALL make the complexity-versus-capacity trade-off
          visible. inventOnly; implemented=false; codeApproved=
          false; no SemVer bump.
        */
        attribute requirementId : String = "MN-REQ-06.9";
      }

      requirement def MN_REQ_06_10_SliceHandCarryAcrossServes {
        doc /*
          OPTIONAL Later invent (#47 cousin; contrast to #191):
          named move SliceHandCarry — a bounded WorkingMemorySlice
          MAY leave one memnet serve and be absorbed into a
          session on another serve (or into a different session
          on the same serve). This is an explicit copy, not
          ClusterRoute, not a live hop, and not import_slice
          across hosts. Engine/tip topology (tip≠face). SHALL
          NOT be the SysMLEdge product face, an AccountFace UI,
          or InvenTree. SHALL NOT nest under MemNetSystem.
          Path SHALL be export_pin_map or session_save, then
          operator file copy on the LAN, then import or
          session_load on the destination. import_slice SHALL
          be allowed only when both sessions already live on
          the SAME serve. SHALL NOT invent shipped
          import_slice(from_url). SHALL NOT teach dest-side
          absorb of a remote URL as import_slice.
          Source session SHALL stay on its owning serve. Dest
          SHALL be a different session (same host or other host).
          Caps and truncation flags SHALL survive the file.
          A clipped extract SHALL NOT look complete.
          Commit / mutate SHALL stay the dest session's owning
          serve gate after absorb. Neo4j shared graph DB is
          retired (#189) and SHALL NOT be the pipe. Distinct
          from MN-REQ-06.9 (ClusterRoute: where the session
          lives; pin_map / find SHALL NOT span backends).
          inventOnly; implemented=false; codeApproved=false;
          no SemVer bump. Public operator text: InkMirage only.
        */
        attribute requirementId : String = "MN-REQ-06.10";
      }

      requirement def MN_REQ_06_11_AdminServeUsageReport {
        doc /*
          SHALL expose a read-only admin usage report on memnet-serve
          (TcpServeBridge / LocalIpcGateway argv proxy; optional
          envelope admin_usage entry). InkMirage admin MCP / face
          MAY call it later; this repo SHALL NOT nest that admin
          MCP. Distinct from MN-REQ-06.5 (human dashboard may list
          live ids; HTTP parked). This report is admin-only.
          Credential: a serve-process env secret
          (MEMNET_ADMIN_TOKEN), not CapsPolicy agent ACL and not
          MEMNET_CALLER. When that env is unset or blank, the call
          SHALL refuse with named @ERR: admin_unconfigured and
          SHALL NOT emit a report body (empty or partial MUST NOT
          look complete). When configured, the caller SHALL present
          the matching token (--token or envelope admin_token);
          mismatch or missing token SHALL @ERR: admin_denied.
          Read-only: SHALL NOT session_open / close / load / save /
          mutate / purge / slide TTL / touch last-access. Peek the
          live registry only.
          Privacy: counts and caps only. SHALL NOT emit graph
          content, node text, locators, or a real session id
          (mn_…). Each session SHALL appear as a stable opaque
          alias (HMAC of the sid keyed by the admin token) plus
          optional product label. Alias rotation when the token
          rotates is accepted.
          Per serve: live registry occupancy against
          MEMNET_MAX_SESSIONS (default 1024). Per session: row
          count against MEMNET_MAX_ROWS, relation-type count
          against MEMNET_MAX_RELATIONS, last access, TTL left,
          and whether process save-on-expire is armed (process
          Caps flag repeated on each row; not a per-session
          arm today). Process: resident memory, uptime, version,
          configured caps. A field that cannot be computed SHALL
          be named in unavailable; the report SHALL still say
          which fields are present. SHALL NOT fill a missing
          field with zero as if measured.
          Cap pressure since serve start: counts of hard
          refusals by @ERR code (limit_exceeded by kind;
          ingest_budget; frame_too_large; acl_*;
          reserve_conflict; session_expired) and counts of
          signalled pin_map Truncation by reason. leftover
          silent clips SHALL NOT increment Truncation.
          Surface: CLI `memnet admin usage-report` proxied by
          serve, plus optional JSON envelope {admin_usage:true,
          admin_token}. SHALL NOT appear on the agent MCP tool
          list (onAgentMcp=false; MN-REQ-07.3). Not GQL agent
          wire. Stdout is one JSON object.
          Product label: CLI session open MAY take optional
          --product (gate-side hint; not required of agents).
          MCP session_open SHALL NOT grow this argument (would
          appear on the agent tool list). Open question
          (mcpProductLabelOpen): how an in-process MCP-only
          gate attaches a product label without changing the
          agent usage method — unbuilt; MUST NOT invent an MCP
          arg in this cut. No SemVer bump.
        */
        attribute requirementId : String = "MN-REQ-06.11";
      }

      requirement def MN_REQ_06_12_ProductGateway {
        doc /*
          SHALL provide MemNetProductGateway as a capability of
          memnet-mcp (MemNetLanMcpFront), not a separate droplet
          shim. Online products (Endleaf now; Atelier and
          SysMLEdge later) SHALL reach a memnet serve only
          through this gateway. tip≠face. SHALL NOT nest under
          MemNetSystem. SHALL NOT bump SemVer for this cut.
          When MEMNET_GATEWAY_CONFIG is unset, memnet-mcp SHALL
          keep today's single backend: in-process by default,
          or one MEMNET_SERVE_HOST and MEMNET_SERVE_PORT when
          MEMNET_MCP_TRANSPORT=tcp.
          Registry: a config file SHALL map each backend id to
          a tailnet host and port. No host literal in code.
          Route by product (the credential), optional house,
          and session. SessionOwnerRegistry row SHALL be the
          one owner. SHALL NOT move a live session onto another
          backend. Failover SHALL apply only when placing a
          new session (session open, or session load from a
          file) and the request names neither house nor
          backend. A named house or backend that is down SHALL
          refuse gateway_backend_unreachable. Owner down on a
          later call SHALL refuse the same way.
          Auth: one credential set per product, stored as sha256
          only, scoped to that product's backends, rotatable by
          adding a hash and revocable by flag. SHALL NOT accept
          mn_tip_ portal keys or MEMNET_MCP_HTTP_TOKEN as this
          credential (MN-REQ-06.8 is a different hop).
          Pass-through: args and stdin SHALL be forwarded
          unchanged. Engine @ERR, @WRN, @STAT and exit_code
          SHALL return as the backend wrote them, except the
          session-list membership filter (filtered n in
          @STAT: sessions|n/max). The gateway SHALL NOT enforce
          MAX_ROWS, mutate batch lines, or value bytes below
          the backend. The only gateway size cap is the
          request-body ceiling (default 4 MiB, contract).
          Each product SHALL pin a backend version. Mismatch
          SHALL refuse gateway_backend_version_mismatch and
          SHALL NOT forward.
          Session open, load, save, close and list SHALL stay
          inside the product namespace. List SHALL omit another
          product's sessions. A foreign or unknown session
          SHALL refuse gateway_forbidden_session.
          Listener SHALL bind loopback or tailnet (100.64.0.0/10
          or Tailscale IPv6) by default. A public bind SHALL
          be refused unless MEMNET_GATEWAY_ALLOW_PUBLIC=1.
          Gateway refusals SHALL be @ERR: gateway_<code>|…
          distinct from engine @ERR. Admin counts SHALL be per
          product and SHALL omit graph content and session ids.
          The #191 catalogue (MCP tool union across backends,
          SnapshotHandCarry) stays inventOnly on
          MemNetLanMcpFront. This leaf is the shipped cut
          (implemented=true).
        */
        attribute requirementId : String = "MN-REQ-06.12";
      }

      requirement def MN_REQ_06_13_ServeRequestIsolation {
        doc /*
          Concurrent memnet serve commands (TCP and the product
          gateway, which forwards to that serve) SHALL isolate
          each request's stdout, stderr, and exit_code. One
          caller's records SHALL NOT appear in another caller's
          envelope. A failed write SHALL NOT come back with
          another call's success text or exit_code 0.
          Capture SHALL be per request (context-local streams).
          A process-wide swap of sys.stdout / sys.stderr is not
          sufficient on a threaded serve. Requests on different
          sessions MAY still run together; isolation SHALL NOT
          require a serve-wide lock.
        */
        attribute requirementId : String = "MN-REQ-06.13";
      }

      requirement def MN_REQ_06_14_SafeServeUpgrade {
        doc /*
          SHALL upgrade a live memnet-serve without silently
          dropping a loaded session. The procedure stays inside
          memnet serve: snapshot every loaded session, restart
          on the new version, reload every session. Same usage
          method (cue then pin_map, mutate). No SemVer bump.
          Patch-level c on 0.19. memnet-mcp and the product
          gateway are outside this procedure. During the restart
          they see serve_draining or a connection error; the
          client pause through it is MN-REQ-06.19. There is no
          helper that edits a systemd unit or a gateway version
          pin.
          Admin drain: credential MEMNET_ADMIN_TOKEN (same gate as
          MN-REQ-06.11; unset admin_unconfigured; mismatch
          admin_denied). Command `memnet admin upgrade-prepare`
          and envelope {upgrade_prepare:true, admin_token}. Not an
          agent MCP tool (onAgentMcp=false).
          Drain enters quiesce. It refuses a new command with
          @ERR: serve_draining|retry_after_s=<seconds>. It
          finishes commands already in flight, then snapshots
          every loaded session through the lossless snapshot path
          (MN-REQ-01.9). It writes a manifest in the state dir
          (MEMNET_STATE_DIR): session ids, row and edge counts,
          checksums, serve version, snapshot format version.
          A session that cannot be saved (snapshot_unsaveable and
          any other save failure) SHALL be named in the report.
          ready_to_stop SHALL stay false unless the operator passes
          the explicit allow-unsaved override. A session MUST NOT
          be lost silently.
          New serve startup reads that manifest, reloads every
          saved session, and checks counts and checksums. It
          reports @STAT: upgrade_restore|ok|n|failed|m. It keeps
          the snapshot files. A snapshot written by an older patch
          (format v1) SHALL load. If the format is unsupported or
          a snapshot is corrupt, startup SHALL fail loudly and
          SHALL NOT delete or rewrite the snapshot files.
          A clean restore (failed = 0) of the upgrade set SHALL
          retire the manifest inside that same startup, before the
          process accepts work. The operator does not run a
          separate retire command. Retire is an audit mark only
          ("retired": true and "retired_at"; the manifest keeps its
          mtime, upgrade.py:745-770): a retired manifest SHALL stay
          a restore candidate, so a later restart restores again
          from the newest valid set under MN-REQ-06.17. A failed
          restore SHALL NOT retire. Start-up reads both the upgrade
          manifest and the checkpoint manifest (MN-REQ-06.17);
          upgrade-prepare stamps "timestamp" in the ready manifest
          and in the blocked report (upgrade.py:370, :349).
          Restored sessions keep the same session id, CapsPolicy
          ACL bindings, TTL expiry clock, and house (the session
          tag map). Product label is kept with the passport.
          Operator: install the new venv, run upgrade-prepare,
          check ready_to_stop, restart the unit on the new venv,
          read the restore stat. To roll back, point the unit at
          the old venv. No real session id in docs or tests.
        */
        attribute requirementId : String = "MN-REQ-06.14";
      }

      requirement def MN_REQ_06_15_ServeCheckpoint {
        doc /*
          SHALL checkpoint every loaded session to disk without
          draining the serve and without refusing traffic.
          Patch-level c on 0.19. Same usage method (cue then
          pin_map, mutate). No SemVer bump.
          Admin credential MEMNET_ADMIN_TOKEN (same gate as
          MN-REQ-06.11 and MN-REQ-06.14; unset
          admin_unconfigured; mismatch admin_denied).
          Command `memnet admin checkpoint` and envelope
          {checkpoint:true, admin_token}. Restore-test helper
          `memnet admin checkpoint-verify <dir>`. Neither is an
          agent MCP tool (onAgentMcp=false).
          For each loaded session, take that session's lock only
          long enough to serialise a consistent copy. Other
          sessions keep serving. A new session open SHALL NOT
          be refused (refusesNewSessionOpen=false). The serve
          SHALL NOT enter quiesce (drainsServe=false).
          Write the copy through the lossless snapshot path
          (MN-REQ-01.9), atomically (temp file, fsync, rename),
          to <MEMNET_STATE_DIR>/checkpoint/<session>.snap.
          Overwrite the previous checkpoint for that session.
          Remove checkpoint files for sessions that are no
          longer loaded. A skipped session SHALL NOT keep an
          older snap in that directory: the directory after a
          run holds one snap per session saved in that run.
          Write checkpoint-manifest.json in that directory.
          Reuse the upgrade manifest row (session, rows, edges,
          checksum) plus serve version, snapshot format version,
          and a timestamp.
          A session that cannot be saved (snapshot_unsaveable
          and the reason) SHALL be named and skipped. It SHALL
          NOT fail the other sessions. The exit code SHALL be
          non-zero when any session was skipped. Print
          @STAT: checkpoint|ok|n|skipped|m|bytes|b.
          SHALL NOT slide TTL or expiry clocks, and SHALL NOT
          change session ids, CapsPolicy ACL, or live state.
          A checkpoint SHALL NOT retire a manifest and SHALL
          NOT load a snapshot into the live registry: the
          checkpoint command still only writes. Serve start-up
          restore reads checkpoint-manifest.json as one of its
          two candidates and may load that set (MN-REQ-06.17);
          restore never writes the checkpoint manifest.
          checkpoint-verify loads every snapshot in the given
          directory into a throwaway in-process store and
          checks row counts, edge counts, and checksums against
          the manifest. It prints
          @STAT: checkpoint_verify|ok|n|failed|m.
          A corrupt or missing snapshot file SHALL fail that
          check. The weekly restore test runs this helper on a
          restic-restored copy. No real session id in docs or
          tests.
        */
        attribute requirementId : String = "MN-REQ-06.15";
      }

      requirement def MN_REQ_06_16_SnapshotAcl {
        doc /*
          SHALL persist the session CapsPolicy ACL in every session
          snapshot written by session save, expire save, checkpoint,
          and safe upgrade: enabled flag, per-caller grants (pin_map,
          mutate, WorkerWriteScope), and optional bind. session_load
          SHALL restore it, including the keep_id reload path.
          The ACL SHALL be one comment line (#@ACL:) after @SNAP.
          @SNAP is version 2 for every snapshot this patch writes.
          A version 2 snapshot with no ACL line SHALL fail the load
          with bad_snapshot. Only a version 1 snapshot (written before
          the ACL was persisted) SHALL load with ACL off, and the load
          output SHALL say so (@ACL: absent|off). Loaders SHALL still
          accept version 1. A malformed ACL line SHALL fail the load;
          it SHALL NOT silently load with ACL off. The load output
          SHALL NOT print the bind lease. The bind SHALL store only the
          SHA-256 of the lease, and the caller re-presents the lease to
          mutate; the snapshot and the upgrade passport SHALL NOT hold
          the raw lease. Snapshot files and the upgrade and checkpoint
          manifests SHALL be written atomically (0600 temp file, fsync,
          rename) at mode 0600. The snapshot and the upgrade passport
          share one ACL serialiser. A save SHALL refuse when the ACL
          does not reload to the same grants. Malformed bind (no lease
          digest, not a dict, or no mission_id) SHALL fail bad_snapshot.
          The first format 2 write over a format 1 file SHALL first copy
          the v1 bytes once to <file>.v1.bak at mode 0600; an existing
          backup SHALL NOT be overwritten; no dual write. Rollback to
          0.19.23 restores the .v1.bak files; writes after the upgrade
          are lost, and an old build refuses v2 loudly. No SemVer bump.
        */
        attribute requirementId : String = "MN-REQ-06.16";
      }

      requirement def MN_REQ_06_17_RestartRestoreNewestSet {
        doc /*
          Status: implemented. Restart restore from the newest valid
          snapshot set. Before this cut start-up read only the upgrade
          manifest and skipped it silently once retired, so a restart
          after a checkpoint came up with 0 sessions. Code refs at
          d64bedf, parts/common/memnet/memnet/upgrade.py; serve.py and
          local_ipc_gateway.py call startup_restore_or_exit unchanged.
          (1) Candidates. With state root R (MEMNET_STATE_DIR, else the
          default state dir), every serve start SHALL consider two
          snapshot sets (upgrade.py:472-480): "checkpoint",
          R/checkpoint/checkpoint-manifest.json, whose row file SHALL be
          a single name under R/checkpoint (any other value makes the
          set invalid, upgrade_manifest; upgrade.py:483-495); and
          "upgrade", R/upgrade-manifest.json, whose row file is relative
          to R. upgrade-blocked.json is never a candidate.
          (2) Timestamp. A set's time SHALL be the manifest "timestamp"
          when it parses as ISO-8601 with a UTC offset or Z, else the
          manifest file mtime as UTC, recorded as timestamp_source
          "manifest" or "mtime" (upgrade.py:459-469, :546-552). Legacy
          upgrade manifests have no timestamp and fall back to mtime.
          (3) Order. Newest first; on an exact tie the upgrade set goes
          before the checkpoint set, because it was taken drained
          (upgrade.py:446, :579-581).
          (4) Retired. "retired" SHALL NOT remove a candidate. It means
          the upgrade set was restored cleanly at least once and is kept
          for audit with "retired_at". Every later restart restores
          again. Restore SHALL NOT write the checkpoint manifest.
          (5) Pre-flight. Before anything is loaded, with no registry
          change, each set SHALL be checked (upgrade.py:498-532): the
          JSON loads and is an object, else upgrade_manifest; for
          "upgrade", ready_to_stop is true, else upgrade_not_ready; the
          snapshot format is supported, else upgrade_snapshot_format;
          sessions is a list of objects, else upgrade_manifest; for
          every row the file exists (snapshot_not_found), its sha256
          equals checksum_sha256 (upgrade_checksum) and its body after
          the passport starts with the snapshot magic (bad_snapshot).
          (6) Choice and fallback. The first set in that order that
          passes pre-flight SHALL be loaded. Every newer set that
          failed SHALL be reported loudly, one line per set on stdout
          and on stderr, @WARN: restore_fallback|<source>|<code>|<detail>,
          and one {source, code, detail} entry in the report's
          "rejected" (upgrade.py:689-695, :734-735). A corrupt newest set
          therefore falls back to the older intact one and says so on
          every start.
          (7) None. No candidate file at all SHALL be skipped (a fresh
          state dir; 0 sessions, no line). Candidates present but none
          valid SHALL raise the newest set's own code: start-up prints
          @ERR: <code>|<detail> and exits 3 (upgrade.py:696-698,
          :728-731). A manifest on disk SHALL never give a silent 0.
          (8) Load. The chosen set loads as before (keep_id,
          preserve_clocks; counts, house, session id and the
          mutated-file rollback; upgrade.py:595-673). Checkpoint rows
          have no passport: the ACL comes from the snapshot #@ACL line,
          the product from the row, and the clock check compares the
          row expires_at (upgrade_clock). A registry that is not empty
          is refused upgrade_restore_registry_busy. A failure while
          loading a set that passed pre-flight is a per-session failure:
          start-up exits 3 with no fallback (upgrade.py:738-739).
          (9) Empty. A valid newest set with no sessions wins: it
          records that nothing was loaded, so older sessions are not
          brought back.
          (10) Report. upgrade-restore.json keeps every key and adds
          source, timestamp, timestamp_source, manifest (path relative
          to R) and rejected (upgrade.py:413-428). Start-up prints
          @STAT: restore_source|<source>|<timestamp> and then the
          unchanged @STAT: upgrade_restore|ok|n|failed|m, each on stdout
          and stderr. Retire (MN-REQ-06.14) runs only when the source is
          upgrade and failed = 0 (upgrade.py:740-742).
          (11) Interface. RestoreCandidate (source, manifest_path,
          snap_root, timestamp, timestamp_source, error_code,
          error_detail) and restore_candidates(directory=None), newest
          first, pre-flight done, read only (upgrade.py:431-440,
          :585-587); RestoreReport gains source, timestamp, rejected;
          restore_manifest, startup_restore_or_exit and retire_manifest
          keep their names and signatures.
          (12) Accepted risk. A restart replays the newest set, so a
          session closed after that set was written comes back until
          the next checkpoint. Operators run memnet admin checkpoint
          after closing sessions and before a planned restart; the
          hourly checkpoint bounds the rest. Both manifests are stamped
          by a running serve; on a host without a real-time clock,
          restart after the clock has synchronised.
          Same usage method; no SemVer bump. No real session id in docs
          or tests. Verify: MN-VER-06-S15. Behaviour:
          RestartRestoreChoice. Evidence: tests/test_restart_restore.py,
          tests/test_safe_upgrade.py::test_clean_restore_retires_and_a_later_start_still_restores.
        */
        attribute requirementId : String = "MN-REQ-06.17";
      }

      requirement def MN_REQ_06_18_McpExtraFailFast {
        doc /*
          Status: implemented. memnet-mcp fails fast without the [mcp]
          extra. Before this cut a plain install crash-looped the unit
          with an ImportError traceback before main ran.
          (1) The memnet-mcp console entry SHALL be
          memnet_mcp.entry:main (pyproject.toml [project.scripts]);
          python -m memnet_mcp SHALL call the same main
          (memnet_mcp/__main__.py). Before it parses any argument, main
          SHALL import mcp.server.fastmcp and then uvicorn
          (memnet_mcp/entry.py:14-32).
          (2) On the first missing module it SHALL write exactly one
          line to stderr, nothing to stdout and no traceback, and exit
          2: @ERR: mcp_extra_missing|memnet-mcp needs the mcp extra
          (missing module: <mcp|uvicorn>); install with: pip install
          'memnet-llm[mcp]'. The hint is MCP_EXTRA_HINT.
          (3) Every transport (stdio, streamable-http, the product
          gateway) needs the extra, and --help without it gives the same
          one line: one install rule for every memnet-mcp unit.
          (4) The server module keeps its own import guard for direct
          imports, quoting the hint the same way. Install and upgrade
          docs SHALL say that any host running memnet-mcp installs
          memnet-llm[mcp] (README.md; docs/operations/safe-upgrade.md
          step 1; product-gateway-contract.md; memnet-lan-mcp-front.md).
          The memnet CLI and memnet serve do not need the extra. No
          SemVer bump. Verify: MN-VER-06-S16. Evidence:
          tests/test_mcp_extra_missing.py.
        */
        attribute requirementId : String = "MN-REQ-06.18";
      }

      requirement def MN_REQ_06_19_RestartSafeTransport {
        doc /*
          Status: implemented. Owner goal t1305u: an upgrade may
          pause callers, but sessions SHALL work after it. A restart
          or drain of memnet serve, memnet-mcp-http or the product
          gateway SHALL pause callers by bounded retry. It SHALL NOT
          drop an MCP session or fail a durable in-flight read. A
          write SHALL NOT be silently replayed.
          (1) memnet-mcp streamable-http is stateless: FastMCP
          stateless_http=true and json_response=true
          (memnet_mcp/server.py). No tool keeps per-MCP-session
          state; the MemNet session is a tool argument. After a
          restart, a tools/call with no Mcp-Session-Id header works.
          (2) ServePool.send (memnet/serve_pool.py) retries within
          MEMNET_SERVE_RETRY_S (default 30 s; 0 turns retry off)
          with exponential backoff and jitter (0.1 s doubling, cap
          2 s). Retry any request that was not delivered: connect
          refused or reset, or the frame not fully written (the
          serve acts only on a whole frame). Retry any request the
          serve refused with @ERR: serve_draining|retry_after_s=N,
          after at least N seconds. When the budget runs out, the
          last connect error or the draining envelope surfaces.
          (3) A reset after the whole frame was written is retried
          for READ requests only. A WRITE surfaces the error and is
          delivered once. One module classifies requests
          (memnet/serve_retry.py): a READ allowlist (version,
          guide, examples, map show and fields, relations list,
          session current, list, resume and expire-status, read
          list, query pin-map, warm, find, walk, typed-walk,
          neighbors, path and context, housekeep stats, stale,
          orphans, dangling and recyclable, export pin-map without
          --out, admin usage-report). Every other request is a
          WRITE, so an unknown verb is never replayed.
          (4) The product gateway and the memnet-mcp tcp client
          inherit (2) and (3) through send_command. Neither gates on
          probe first. The gateway caches no failed version check.
          One retry loop only; the gateway adds no budget of its own.
          No SemVer bump. Verify: MN-VER-06-S17. Evidence:
          tests/test_serve_restart_retry.py,
          tests/test_mcp_http.py::test_tools_call_works_after_restart_without_session_header.
        */
        attribute requirementId : String = "MN-REQ-06.19";
      }
    }

    // ----- MCP agent boundary -----

    requirement def MN_REQ_07_McpAgentBoundary {
      doc /*
        Group: generic MCP/CLI tool surface for MemNet; TARGET is
        cue/pattern only (no store-key id); leftover id tools are not
        product commands; no domain-product tools.
      */
      attribute requirementId : String = "MN-REQ-07";

      requirement def MN_REQ_07_1_GenericToolSurface {
        doc /*
          SHALL expose a TARGET generic MCP/CLI tool surface (same two
          operators: Recall + Commit): session_open / current / save / load /
          list / close
          (session handle is not a graph store key); find (bounded MATCH by
          kind / labels / properties / keyword, hard LIMIT — the cue when
          no nickname exists); pin_map as a shaped neighbourhood walk from
          a cue/pattern (labels+props; optional nickname id if the agent
          set one — SHALL NOT require a store-key anchor); mutate as one
          Commit of GQL (CREATE () legal; MERGE/SET/DELETE by
          labels+properties; edge = type + two end elements; no NEW; no
          AssignedIdMap); Path-B ingest (locators qname/path/refdes/… are
          properties, not PK; no client NEW; no allocate_from_locator as
          identity); Path-B import (match by labels+properties, not
          MERGE-by-id remint). SHALL NOT nest leftover 0.9 read_get(id),
          NEW / [NEW], AssignedIdMap, add/update that fail without a
          ground store-key, pin_map(anchor=<required id>) as the only pin
          form, allocate_from_locator, import_slice id_policy
          keep|reject|remint keyed on store-key, or elementId/handle on
          the wire as product commands (those remain leftover_* engine
          honesty). Optional engine/status probe and housekeep stats MAY
          remain. In-process by default (MN-REQ-06.1).
        */
        attribute requirementId : String = "MN-REQ-07.1";
      }

      requirement def MN_REQ_07_2_StructuredToolEnvelope {
        doc /*
          SHALL return each MCP tool result in a structured envelope carrying
          exit status, stdout payload, and stderr/error lines.
        */
        attribute requirementId : String = "MN-REQ-07.2";
      }

      requirement def MN_REQ_07_3_NoDomainProductTools {
        doc /*
          Domain-product tools SHALL NOT be embedded in the generic MemNet MCP
          boundary.
        */
        attribute requirementId : String = "MN-REQ-07.3";
      }

      requirement def MN_REQ_07_4_McpLawSeedOnOpen {
        doc /*
          MCP session_open SHALL auto-seed engine-law rows when they are
          missing from the session.
        */
        attribute requirementId : String = "MN-REQ-07.4";
      }

      requirement def MN_REQ_07_5_NoStoreKeyToolSurface {
        doc /*
          TARGET agent/CLI/MCP I/O SHALL NOT key tools on a store-key id.
          Optional NicknameIdProperty MAY seed find/pin_map/mutate when
          the agent set one — it is not identity (MN-REQ-02.8).
          HiddenStoreHandle / elementId SHALL NOT be taught on the wire.
          Leftover 0.9 read_get(id), NEW / IdAllocator as a product verb,
          AssignedIdMap as required emit, add/update that fail without a
          ground store-key, pin_map require_anchor as the only pin form,
          ingest allocate_from_locator / MERGE-by-id, and import_slice
          id_policy keep|reject|remint keyed on store-key SHALL remain
          leftover_* engine honesty (implemented leftover) — MUST NOT
          nest under McpFacade / CliFacade as product commands. TARGET
          implemented=false for those leftover commands. Path-B TARGET
          ingest/import is pattern match (labels+properties); leftover
          mint laws are not TARGET commands.
        */
        attribute requirementId : String = "MN-REQ-07.5";
      }
    }

    // ----- Agent I/O grammar (stdio + MCP) -----

    requirement def MN_REQ_08_AgentIoGrammar {
      doc /*
        Group: LLM-friendly grammar on agent-facing I/O. MemNet agent I/O
        (stdio pin-map emit; MCP tool args/results that carry memory language)
        is produced and consumed by an LLM, so presentation SHALL follow
        prompt rules. One agent dialect teach = openCypher-shaped GQL
        (ADR-001); Write = display = shaped pin_map subgraph both ways.
        Agent I/O SHALL NOT key commands on a store-key id (MN-REQ-07.5).
        Layer / Tier A are archived (not product accept); @TAG pipe remains
        import-once only.
      */
      attribute requirementId : String = "MN-REQ-08";

      requirement def MN_REQ_08_1_LlmFriendlyStdio {
        doc /*
          SHALL present an LLM-friendly grammar on CLI/stdio agent I/O:
          low-noise, learnable, and accurate when presenting facts.
        */
        attribute requirementId : String = "MN-REQ-08.1";
      }

      requirement def MN_REQ_08_2_LlmFriendlyMcp {
        doc /*
          SHALL present an LLM-friendly grammar on MCP tool payloads that
          agents read or write.
        */
        attribute requirementId : String = "MN-REQ-08.2";
      }

      requirement def MN_REQ_08_3_NoHostilePositionalDump {
        doc /*
          Agent-facing I/O SHALL NOT rely on hostile positional dumps that
          burn tokens or invite routine field-count and escape errors,
          contradicting MN-REQ-00 token economy and factual accuracy.
        */
        attribute requirementId : String = "MN-REQ-08.3";
      }

      requirement def MN_REQ_08_4_BoundaryFriendlyIfInternalDiffers {
        doc /*
          Store-internal representation MAY differ from the agent grammar only
          if every agent boundary still presents the friendly surface.
          Internal store records MAY differ; legacy pipe import-once is allowed. Pipe
          SHALL NOT appear as a standing agent-facing dialect on pin-map read
          or mutate/write.
        */
        attribute requirementId : String = "MN-REQ-08.4";
      }

      requirement def MN_REQ_08_5_IoActorIsLlm {
        doc /*
          Agent-facing MemNet I/O SHALL be designed as produced and consumed
          by an LLM (not primarily by hand-written UI forms).
        */
        attribute requirementId : String = "MN-REQ-08.5";
      }

      requirement def MN_REQ_08_6_FollowPromptRules {
        doc /*
          Agent-facing I/O grammar and presentation SHALL follow prompt rules:
          low-noise; accurate, precise, consistent, and coherent fact
          presentation; template-copyable shapes; write equals display.
          Named constraint family -- examples include WDC and novel-cut
          prompt-rule doctrines; not a novel-writer product dependency.
        */
        attribute requirementId : String = "MN-REQ-08.6";
      }

      requirement def MN_REQ_08_7_WriteApproxDisplay {
        doc /*
          Agent-facing emit and accept shapes SHALL be the same dialect:
          what the LLM writes is what it (and humans) read back -- Write =
          display -- so prompts need not teach a second grammar.
        */
        attribute requirementId : String = "MN-REQ-08.7";
      }

      requirement def MN_REQ_08_8_TemplateCopyableShapes {
        doc /*
          Agent-facing records SHALL use template-copyable shapes the LLM can
          imitate from few examples without inventing column order or escape
          tricks.
        */
        attribute requirementId : String = "MN-REQ-08.8";
      }

      requirement def MN_REQ_08_9_PinMapEmitSameAsMutate {
        doc /*
          Live pin map emit SHALL be a shaped subgraph in the same GQL /
          property-graph family as accepted mutate input (redefined Write =
          display). SHALL NOT present raw tabular RETURN as primary read, nor
          a second peer dialect on read vs GQL on write.
        */
        attribute requirementId : String = "MN-REQ-08.9";
      }
    }

    // ----- Human inspection (canonical parser) -----

    requirement def MN_REQ_09_HumanInspect {
      doc /*
        Group: humans and tools recover structure from the grammar via one
        canonical parser (grammar = language; parser = structure recovery).
      */
      attribute requirementId : String = "MN-REQ-09";

      requirement def MN_REQ_09_1_CanonicalParserSsot {
        doc /*
          SHALL provide a single canonical parser (one SSOT parse path) that
          recovers NODE and EDGE structure (kind, optional nickname id,
          fields, endpoints) from the agent-facing grammar, including
          lawful escape rules. SHALL NOT require property id to parse.
          Grammar parse front is GraphGlot; leftover lowering to store
          records remains after the product gate. SHALL NOT require a
          store key or invent a replacement for leftover by_id /
          id_first / NEW.
        */
        attribute requirementId : String = "MN-REQ-09.1";
      }

      requirement def MN_REQ_09_2_RejectInvalidWire {
        doc /*
          The canonical parser SHALL reject invalid wire rather than silently
          mis-split fields.
        */
        attribute requirementId : String = "MN-REQ-09.2";
      }

      requirement def MN_REQ_09_3_ParseFaithfulInspect {
        doc /*
          Humans and tools SHALL be able to inspect what MemNet knows via a
          parse-faithful render or read path that uses the canonical parser.
        */
        attribute requirementId : String = "MN-REQ-09.3";
      }

      requirement def MN_REQ_09_4_NoAdHocConsumerSplits {
        doc /*
          Ad-hoc consumer splits (e.g. naive delimiter split) SHALL NOT be the
          supported inspection or ingest path.
        */
        attribute requirementId : String = "MN-REQ-09.4";
      }

      requirement def MN_REQ_09_5_GraphGlotParseThenProductGate {
        doc /*
          Accept SHALL parse agent GQL with GraphGlot (PyPI graphglot; official
          grammar front), then run a separate MemNet product gate that rejects
          Layer / Tier A and free WITH / UNWIND / CALL / unbounded MATCH…RETURN
          even when GraphGlot parses them. Goldfish bounds stay (pin_map +
          mutate / bounded find). SHALL NOT claim TCK compliance. SHALL NOT
          vendor GraphGlot source. implemented=true only when Python actually
          calls graphglot on the accept path.
        */
        attribute requirementId : String = "MN-REQ-09.5";
      }
    }

    // ----- LLM properties (assumptions) and MemNet limitations -----

    requirement def MN_REQ_10_LlmPropertiesAndLimits {
      doc /*
        Group: assumed properties of the LLM agents MemNet serves, and the
        MemNet limitations that follow. Attribute values document assumed
        properties (true = property is assumed to hold for design). Nested
        leaves are atomic SHALLs/SHOULDs MemNet must respect or compensate for.
        These underpin MN-REQ-00 token economy and factual accuracy.
      */
      attribute requirementId : String = "MN-REQ-10";

      // Assumed LLM properties (design assumptions -- not product SHALLs)
      attribute unreliableCrossTurnMemory : Boolean = true;
      attribute finiteContextWindow : Boolean = true;
      attribute costlyTokensAndToolRoundTrips : Boolean = true;
      attribute inventsIdsWithoutGroundTruth : Boolean = true;
      attribute weakAtBrittlePositionalFormalism : Boolean = true;
      attribute strongAtEnglishAndLowNoiseTemplates : Boolean = true;

      requirement def MN_REQ_10_1_NoChatAsDurableStore {
        doc /*
          SHALL NOT treat chat context as the durable store of pipeline facts
          (LLMs have unreliable cross-turn working memory).
        */
        attribute requirementId : String = "MN-REQ-10.1";
      }

      requirement def MN_REQ_10_2_PinMapMustFitContext {
        doc /*
          Re-injected live pin maps SHALL be sized to fit a finite context
          window.
          window and token budget.
        */
        attribute requirementId : String = "MN-REQ-10.2";
      }

      requirement def MN_REQ_10_3_MinimiseTokenRoundTrips {
        doc /*
          Agent-facing I/O SHALL minimise unnecessary token burn and tool
          round-trips when re-presenting the same facts.
        */
        attribute requirementId : String = "MN-REQ-10.3";
      }

      requirement def MN_REQ_10_4_ExternalGroundTruthRequired {
        doc /*
          Facts that must stay accurate SHALL be grounded in MemNet (or via
          MemNet from search), not invented ids or claims in chat alone.
        */
        attribute requirementId : String = "MN-REQ-10.4";
      }

      requirement def MN_REQ_10_5_GrammarMustBeLlmLearnable {
        doc /*
          Agent-facing grammar SHALL be LLM-learnable: low noise, not a brittle
          positional or escape-heavy formalism that invites routine errors.
        */
        attribute requirementId : String = "MN-REQ-10.5";
      }

      requirement def MN_REQ_10_6_PreferTemplateFriendlyPins {
        doc /*
          Agent-facing presentation SHOULD favour English or structured
          low-noise pins with clear templates where the LLM is strong.
        */
        attribute requirementId : String = "MN-REQ-10.6";
      }

      requirement def MN_REQ_10_7_HumanVerifyViaParser {
        doc /*
          Humans SHALL be able to verify what MemNet knows via the canonical
          parser path, compensating for LLM invention without ground truth.
        */
        attribute requirementId : String = "MN-REQ-10.7";
      }
    }

    // ----- Snapshot / interoperability: map of pins -----
    // Distinct from MN-REQ-01.4--01.6 (session file save/load).

    requirement def MN_REQ_11_SnapshotInterop {
      doc /*
        Group: a map of pins -- short accurate anchors and locators into
        SysML v2, codebase, PCBA schematics (Atopile .ato), and agent
        skills/rules, linked as NODE and EDGE so the LLM can navigate without
        swallowing the whole source. Selective projection means pin map, not
        a bulky corpus dump. Not session-file persistence (see MN-REQ-01.4
        through MN-REQ-01.6).
      */
      attribute requirementId : String = "MN-REQ-11";

      requirement def MN_REQ_11_13_MapOfPins {
        doc /*
          Every MN-REQ-11 snapshot or export SHALL be a map of pins: short
          accurate anchors and locators linked as NODE and EDGE, sufficient
          for LLM navigation. SHALL NOT be a complete copy of the source
          artefact or a bulky corpus dump (same spirit as pin-map economy).
        */
        attribute requirementId : String = "MN-REQ-11.13";
      }

      requirement def MN_REQ_11_1_ExportGraphToSysmlV2 {
        doc /*
          SHALL support exporting a pin map of in-memory NODE and EDGE facts
          into a SysML v2 model representation for the in-repo model-based
          workflow (sysml-models). SHALL NOT require dumping the entire
          session graph.
        */
        attribute requirementId : String = "MN-REQ-11.1";
      }

      requirement def MN_REQ_11_2_NodeMapsToSysmlStructure {
        doc /*
          On SysML export, each MemNet NODE included in the pin map SHALL map
          to a SysML v2 structural element analogue (e.g. part, item, or
          attribute usage) -- an isomorphic projection of the pins, not a
          claim that the SysML metamodel defines literal NODE types, and not
          a requirement to export every store row.
        */
        attribute requirementId : String = "MN-REQ-11.2";
      }

      requirement def MN_REQ_11_3_EdgeMapsToSysmlConnection {
        doc /*
          On SysML export, each MemNet EDGE included in the pin map SHALL map
          to a SysML v2 connection or relationship analogue between the
          mapped structural elements -- projection of the pins only, not
          literal EDGE metamodel types.
        */
        attribute requirementId : String = "MN-REQ-11.3";
      }

      requirement def MN_REQ_11_4_DistinctFromSessionSnapshot {
        doc /*
          Pin maps (SysML export, codebase, PCBA schematics via Atopile .ato,
          skills/rules) SHALL be distinct from named-session file save and
          load (MN-REQ-01.4 through MN-REQ-01.6), which persist
          working-memory session state. Session save/load MUST NOT be taken
          as satisfying these projections, and these projections MUST NOT be
          taken as a full-fidelity session backup or corpus dump.
        */
        attribute requirementId : String = "MN-REQ-11.4";
      }

      requirement def MN_REQ_11_5_SysmlRoundTripShould {
        doc /*
          Round-trip of the SysML pin map back into MemNet NODE and EDGE form
          SHOULD be supported where practical. Full-fidelity recovery of
          original SysML sources from the pins SHALL NOT be required; lossy
          cases SHALL be documented.
        */
        attribute requirementId : String = "MN-REQ-11.5";
      }

      requirement def MN_REQ_11_6_SnapshotCodebaseIntoGraph {
        doc /*
          SHALL support ingesting a pin map of a codebase into the Net of
          Memory as NODE and EDGE locators so agents can fetch a pin map, walk, and
          navigate purpose-relevant structure without swallowing the tree.
          SHALL NOT require indexing every file, symbol, or line.
        */
        attribute requirementId : String = "MN-REQ-11.6";
      }

      requirement def MN_REQ_11_7_CodebaseNodesAreModulesSymbols {
        doc /*
          A codebase pin map SHALL represent selected files or modules and
          symbols (functions, variables, types, and similar) as NODE pins --
          short anchors, not free prose blobs or an exhaustive inventory.
        */
        attribute requirementId : String = "MN-REQ-11.7";
      }

      requirement def MN_REQ_11_8_CodebaseEdgesAreRelations {
        doc /*
          A codebase pin map SHALL represent selected relations among those
          pins (defines, calls, includes, owns, uses, and similar) as
          first-class EDGEs -- not every possible edge in the corpus.
        */
        attribute requirementId : String = "MN-REQ-11.8";
      }

      requirement def MN_REQ_11_9_SnapshotAtoIntoGraph {
        doc /*
          SHALL support ingesting a pin map of PCBA schematics from Atopile
          (.ato projects or files) into the Net of Memory as NODE and EDGE
          locators so agents can fetch a pin map, walk, and navigate purpose-relevant
          connectivity without swallowing the drawing. Atopile .ato is the
          PCBA schematic source for this pin map -- not a separate ingest
          pipeline. SHALL NOT require a complete schematic dump or a copy of
          every .ato artefact.
        */
        attribute requirementId : String = "MN-REQ-11.9";
      }

      requirement def MN_REQ_11_10_SnapshotSkillsAndRulesIntoGraph {
        doc /*
          SHALL support ingesting a pin map of agent skills and rules
          (Cursor/agent SKILL.md packs, .mdc rules, and similar) into the Net
          of Memory as NODE and EDGE locators. SHALL NOT require copying
          every skill body or rule file verbatim into the graph.
        */
        attribute requirementId : String = "MN-REQ-11.10";
      }

      requirement def MN_REQ_11_11_SkillsAndRulesAreNodes {
        doc /*
          A skills/rules pin map SHALL represent selected skill packs and
          rules as NODE pins -- short anchors, not free prose blobs or an
          exhaustive catalogue of every installed pack.
        */
        attribute requirementId : String = "MN-REQ-11.11";
      }

      requirement def MN_REQ_11_12_SkillsRulesEdgesAreRelations {
        doc /*
          A skills/rules pin map SHALL represent selected relations among
          those pins (paired_with, triggers, governs, and similar) as
          first-class EDGEs.
        */
        attribute requirementId : String = "MN-REQ-11.12";
      }

      requirement def MN_REQ_11_14_PcbaAtoNodesAreNetsComponentsPins {
        doc /*
          A PCBA schematic (Atopile .ato) pin map SHALL represent selected
          nets, components, and pins as NODE pins -- short anchors into the
          schematic, not free prose blobs or an exhaustive inventory of every
          symbol and wire.
        */
        attribute requirementId : String = "MN-REQ-11.14";
      }

      requirement def MN_REQ_11_15_PcbaAtoEdgesAreConnectivity {
        doc /*
          A PCBA schematic (Atopile .ato) pin map SHALL represent selected
          connectivity among those pins (pin-to-net, component-owns-pin, and
          similar) as first-class EDGEs -- not every possible connection in
          the schematic.
        */
        attribute requirementId : String = "MN-REQ-11.15";
      }

      requirement def MN_REQ_11_16_PinIngestDeterministicIds {
        doc /*
          Pin-map ingest (SysML, codebase, PCBA/.ato, skills) SHALL Commit
          create of GraphElement from the source. Locators (path, refdes,
          net, pin, qname, skill_id, and similar) SHALL be properties on
          those elements -- not identity and not a store key. TARGET SHALL
          NOT require ground ids (leftover_by_id as PK). Optional nickname
          id MAY be emitted when present.           leftover_allocate_from_locator
          is leftover 0.9 invented store, not this TARGET and not a
          TARGET product command (MN-REQ-07.5). leftover_NEW_mint
          SHALL NOT be TARGET law for source elements. TARGET Path-B
          ingest is pattern match (labels+properties); leftover
          MERGE-by-id mint is leftover engine honesty.
          Path-B is a keyword and brace walk that Commits GQL pins; it is not a
          SysML v2 parser and has no grammar.
        */
        attribute requirementId : String = "MN-REQ-11.16";
      }

      requirement def MN_REQ_11_17_CatalogModelSnap {
        doc /*
          0.15 Catalog Snap + session strata + model Snap. SHALL Snap one
          SysML load tree into a catalog session plus package interiors
          (optional kind band or child package when an interior exceeds
          about 2M). Catalog pins SHALL carry session= and qname=
          locators (properties, not a store key). List = those session=
          ids. Look = pin_map of one named session. Join = Path-B Absorb
          of a WorkingMemorySlice. SHALL NOT: rank sessions with ANN;
          Absorb a whole S; dump one model into one session or the
          mission; revive Layer / layer=; mint one session per TSK or
          per requirement def; invent a store key; put HiddenStoreHandle
          on the wire. SHALL NOT thicken Recall/Commit into a third
          operator (Snap is Commit of locators; Absorb stays Path-B).
          ingest_sysml 1-path-into-current-session remains Path-B as-is.
          Cross-cut satisfy: MN-REQ-11.17.1.
        */
        attribute requirementId : String = "MN-REQ-11.17";

        requirement def MN_REQ_11_17_1_CrossCutSatisfyLocators {
          doc /*
            When Snap drops a satisfy whose ends live in two interiors of
            the same model Snap, the catalog SHALL Commit locator stubs
            (session= + qname= / requirementId=) and a satisfies edge when
            unique ends fit goldfish M; otherwise a package-pair satisfies
            plus an honest cross_cut warning. Unresolved dest SHALL warn
            cross_cut_miss. Interiors SHALL NOT grow a dangling dest node.
            SHALL NOT merge interiors, Absorb a whole S, or treat a
            foreign product pin_map (SysMLEdge / other desk) as this
            MemNet catalog look. SysMLEdge graph is not MemNet SSOT.
            This engine checkout is repo-based: SSOT is git
            sysml-models/. modelbasedPrj-* is the same (MUST NOT use SysMLEdge as model SSOT).
            Downstream SysMLEdgePrj-* and bound: the desk graph is working model SSOT;
            MemNet stays mission working memory. Look remains one named session per
            generate; join remains Path-B slice.
          */
          attribute requirementId : String = "MN-REQ-11.17.1";
        }

        requirement def MN_REQ_11_17_2_SnapSessionGrain {
          doc /*
            Catalog Snap SHALL mint one catalog session plus a bounded
            number of interiors for one load tree. Grain SHALL be
            top-level package first; optional kind band (REQ / PRT / POR)
            when a package exceeds about 2M and each band has at least
            two non-package nodes; optional nested package (a SysML
            package def, not a two-segment element qname) when that
            nested package itself exceeds about 2M and is not a single
            leaf. SHALL NOT mint one session per part def, per
            requirement def, or per other leaf. SHALL NOT treat
            Package::Element qname as a child-package cut. A mid-size
            model (a few hundred parts and requirements in a handful of
            packages) SHALL stay a handful of sessions (catalog plus
            those packages, plus at most a few kind or nested cuts),
            never hundreds. Single-leaf interiors SHALL NOT be created
            by a split. Recursing a same-kind package until each
            interior fits 2M remains TARGET, not this leaf.
          */
          attribute requirementId : String = "MN-REQ-11.17.2";
        }

        requirement def MN_REQ_11_17_3_SnapBudgetPrecheck {
          doc /*
            Before Catalog Snap mints any session, it SHALL count the
            catalog plus planned interiors against remaining session
            capacity (MEMNET_MAX_SESSIONS unchanged) and SHALL check
            each planned interior against the ingest node and edge
            budgets (max_nodes / max_edges unchanged). If the plan
            does not fit, Snap SHALL refuse with a named @ERR
            (limit_exceeded sessions, or ingest_budget) and SHALL
            create nothing. A mid-way failure SHALL close every session
            this call minted and SHALL leave no partial Snap stack.
            Caps defaults SHALL NOT change.
          */
          attribute requirementId : String = "MN-REQ-11.17.3";
        }

        requirement def MN_REQ_11_17_4_SnapCallerGoneRollback {
          doc /*
            When the serve or IPC caller is gone before Snap finishes
            (client wait exceeded, or the peer socket closed), serve
            SHALL stop minting, roll back sessions this call created,
            and SHALL NOT keep creating strata unseen. The client
            envelope SHALL name the wait: serve_timeout. Serve-side
            stop SHALL name caller_gone. A model of a few hundred
            parts and requirements SHALL finish inside the existing
            client wait (default 30 s unchanged) once grain is bounded.
            SHALL NOT return an error while sessions keep appearing.
          */
          attribute requirementId : String = "MN-REQ-11.17.4";
        }

        requirement def MN_REQ_11_17_5_SnapReplaceByModelIdentity {
          doc /*
            A second Catalog Snap of the same load-tree identity
            (resolved root path) SHALL replace the live stack for that
            identity after the new stack commits, and SHALL NOT leave
            two catalogs for the same root. Identity is the resolved
            root, not a session id. SHALL NOT echo a session id on the
            wire error. Close of the previous stack happens only after
            the new mint succeeds so a failed retry does not destroy
            a complete prior Snap. Caller MAY session_close strata
            first; replace still holds when they do not.
          */
          attribute requirementId : String = "MN-REQ-11.17.5";
        }
      }
    }

    // ----- Multitask Mode (as-is 0.4.x agent operating model) -----
    // Enforceable parent/worker doctrine over a shared session.
    // CapsPolicy ACL is shipped when enabled per session. Neighbourhood
    // reserve is shipped. Path-B PinMapIngest_* domains are shipped
    // (Sysml/Codebase/PcbaAto/SkillsRules). Full private/shared/open +
    // session_token modes remain design-only. Pin-map export (#66) is 0.19
    // cue GQL write-out; re-ingest not claimed.

    requirement def MN_REQ_12_MultitaskMode {
      doc /*
        Group: when Multitask Mode (or Task sub-agents) is active, MemNet
        SHALL be operated as a shared mission store with a parent coordinator
        and scoped workers. Chat is never mission SSOT. As-is product
        constraints for 0.4.x include the shipped, per-session CapsPolicy ACL
        cut; RSV and Path-B PinMapIngest_* domains shipped; full
        private/shared/open + session_token modes deferred.
      */
      attribute requirementId : String = "MN-REQ-12";

      requirement def MN_REQ_12_1_SharedSessionMissionSsot {
        doc /*
          Under Multitask, SHALL use one shared named MemNet session id as the
          mission source of truth for ids, paths, and task state (session as
          SSOT handle for the MissionWorkingSet). Handoff SHALL be by session
          id (SessionHandoff); peers re-pin_map. Chat, tool transcripts, and
          sub-agent prose SHALL NOT be treated as durable mission SSOT
          (extends MN-REQ-10.1 / MN-REQ-01.7 / MN-REQ-01.8).
        */
        attribute requirementId : String = "MN-REQ-12.1";
      }

      requirement def MN_REQ_12_2_SharedStoreTransport {
        doc /*
          Under Multitask, parent and workers SHALL bind to the same shared
          GraphStore/session registry via TCP serve, streamable-http MCP, or
          local IPC when available. Default isolated in-process MCP (one
          graph per host process) SHALL NOT be used for shared Multitask
          missions. Single-agent goldfish MAY still use in-process (MN-REQ-06.1).
        */
        attribute requirementId : String = "MN-REQ-12.2";
      }

      requirement def MN_REQ_12_3_ParentOwnsTaskLifecycle {
        doc /*
          The parent coordinator SHALL mint and own house task and user-
          constraint lifecycle rows (TSK_* / USR_*): create, status=active,
          status=settled, and optional led_to_success edges. Workers SHALL NOT
          settle parent-owned TSK_* / USR_* unless the parent explicitly
          delegated that settle.
        */
        attribute requirementId : String = "MN-REQ-12.3";
      }

      requirement def MN_REQ_12_4_WorkerPinMapAndScopedWrite {
        doc /*
          Each worker turn SHALL begin with a live pin map on the shared
          session, copy assigned ids from that pin map, and mutate only under
          the parent-assigned subgraph (anchors and relation scope). Workers
          SHALL NOT invent ids the parent already minted, and SHALL NOT open a
          different session id unless the parent assigned a separate mission.
        */
        attribute requirementId : String = "MN-REQ-12.4";
      }

      requirement def MN_REQ_12_5_PreferOneWorkerOrDisjoint {
        doc /*
          Multitask missions SHOULD prefer one worker per coherent workstream.
          Asynchronous parallel workers SHALL use disjoint anchor subtrees on
          one shared session OR separate parent-assigned session ids.
          Two writers SHALL NOT mutate the same anchor slice without explicit
          serialisation (MUST NOT dual-write in parallel). CapsPolicy
          hard-rejects mutate outside WorkerWriteScope when session ACL is
          enabled; NeighbourhoodReserve (MN-REQ-12.13) leases ego scopes so
          overlapping writers fail with reserve_conflict rather than
          last-write-wins.
        */
        attribute requirementId : String = "MN-REQ-12.5";
      }

      requirement def MN_REQ_12_6_ParentEndTurnNoPoll {
        doc /*
          After AsyncTaskDispatch (spawning background workers via
          EvDelegateWorker), the parent SHALL EvEndCoordinatorTurn
          (Multitask gate). The parent SHALL NOT poll or await worker
          completion in the same turn, and SHALL NOT redo worker investigation
          from chat memory. On the next coordinator turn the parent SHALL
          pin_map first and act from the refreshed shared-session slice
          (or SessionImportReceive when sessions were separate).
        */
        attribute requirementId : String = "MN-REQ-12.6";
      }

      requirement def MN_REQ_12_7_NoAssumeAclReserveIngest {
        doc /*
          As-is NOW: the CapsPolicy ACL cut IS shipped (engineAclShipped=true)
          when session ACL is enabled. Neighbourhood reserve (RSV, llm_id +
          TTL) IS shipped as NeighbourhoodReserve / MN-REQ-12.13. Path-B
          PinMapIngest_* domains ARE shipped (Sysml / Codebase / PcbaAto /
          SkillsRules; MN-REQ-11.6–11.16; issues #31 / #64; CLI/MCP ingest
          sysml|codebase|pcba|skills). Agents MUST NOT assume the full
          private/shared/open + session_token modes until those ship. Agents
          MUST NOT assume pin-map export / round-trip (MN-REQ-11.1–11.5 / #66)
          from ingest alone.
        */
        attribute requirementId : String = "MN-REQ-12.7";
      }

      requirement def MN_REQ_12_8_AppliesToRelevantTasks {
        doc /*
          Multitask Mode (MN-REQ-12.1 through 12.7) SHALL apply when mission
          work is multi-step, coordinator-delegated to workers, or
          parallelisable across disjoint workers. Trivial one-shot
          single-agent turns SHALL use the ordinary goldfish loop without
          Multitask shared-store or parent/worker obligations.
        */
        attribute requirementId : String = "MN-REQ-12.8";
      }

      requirement def MN_REQ_12_13_NeighbourhoodReserve {
        doc /*
          SHALL provide neighbourhood reserve (RSV) so parallel agents on one
          shared session_id can hold disjoint pin-map ego scopes: required
          llm_id holder, required ttl_s lease, scope = anchor + depth matching
          pin_map. Mutate that touches reserved ids SHALL require matching
          llm_id (else reserved / no_llm_id). Overlap with another holder
          SHALL fail with reserve_conflict. Expired leases SHALL auto-release.
          Pin map MAY surface RSV present lines. Lifecycle via reserve /
          extend / release (MCP/CLI) — not + RSV graph mutate.
        */
        attribute requirementId : String = "MN-REQ-12.13";
      }

      requirement def MN_REQ_12_9_LeadOwnsSessionImport {
        doc /*
          When a team lead imports a member's working memory
          (SessionImportReceive), the lead / parent SHALL own the import into
          the mission session. Path A (prefer shared mission sessionId):
          import is re-pin_map only — no WorkingMemorySlice, no ImportGuard,
          no ImportAbsorb. Path B (separate sessions): lead SHALL
          ImportAbsorb a bounded WorkingMemorySlice under owner-gated
          id_policy keep | reject | remint:
            keep = MERGE as a per-write lookup of labels+props / rel
              type+ends into lead SSOT (GraphElement; not append / not a
              second copy; leftover_MERGE_by_id is leftover, not this keep);
            reject = conflict, no lead mutate;
            remint = leftover_NEW_mint / leftover_by_id for conflicts;
              lead old rows stay; edges retarget -- not TARGET law.
          TARGET Path-B import is pattern match (labels+properties), not
          MERGE-by-id remint as a product command. leftover id_policy
          keep|reject|remint keyed on store-key SHALL remain leftover
          engine honesty — MUST NOT nest as an McpFacade / CliFacade
          command (MN-REQ-07.5).
          Edges after nodes; LAW/vocab SHALL NOT import; lead settles parent
          TSK_*. Chat/transcripts SHALL NOT be the payload (MN-REQ-12.10).
          Members SHALL NOT settle parent-owned TSK_* unless delegated.
          Product verb = import (SessionImport* only — no SessionMerge*).
          Distinct from micro merge=true (in-session re-id).
        */
        attribute requirementId : String = "MN-REQ-12.9";
      }

      requirement def MN_REQ_12_10_NoChatOrWholeStoreImport {
        doc /*
          Session import (SessionImportReceive) SHALL NOT use chat or tool
          transcripts as the import payload (EvImportFromChat forbidden).
          Engine SHALL require anchors on WorkingMemorySliceExport, enforce
          slice budget, and SHALL NOT import a whole-store dump. Dual-writer
          on the target slice during import SHALL NOT be assumed safe (0.4.x
          last-write-wins; MN-REQ-12.7).
        */
        attribute requirementId : String = "MN-REQ-12.10";
      }

      requirement def MN_REQ_12_11_CheapLlmImportGuardSoft {
        doc /*
          OPTIONAL soft policy (never mandatory LLM): Path B
          WorkingMemorySlice import SHOULD pass ImportGuard soft review
          before ImportAbsorb (allow / trim / reject + short reason; trim
          subtractive via keep_ids) when the host enables the guard.
          Nest under SessionImportReceive / ImportGuard (PinMapIngest-style):
          ImportGuardHook = host plug-in (set_import_guard / --no-guard /
          enable_guard; GuardPassthrough when skipped — skipping is valid);
          CheapLlmImportGuard = optional default adapter in memnet-llm (off
          unless MEMNET_IMPORT_GUARD_API_KEY set; does not vendor a model;
          shipped #63). Hook shipped ≠ cheap LLM alone. Path A SHALL
          re-pin_map without ImportGuard. LLM MAY: choose anchors, trim
          junk, advise keep vs remint. Soft guard SHALL NOT replace engine
          hard gates (schema, ACL, slice budget, anchors, LAW exclude,
          id_policy). Guard chat SHALL NOT be SSOT — record
          ImportGuardDecision as structured atoms; lead session remains
          SSOT after import. costTier is a cost/latency class, not a
          vendor id. Host MAY skip/disable (GuardPassthrough / --no-guard).
          Satisfied by CheapLlmImportGuard part (not the hook alone).
        */
        attribute requirementId : String = "MN-REQ-12.11";
      }

      requirement def MN_REQ_12_12_HostDrivenAsyncParallel {
        doc /*
          Asynchronous parallel Multitask: parent opens/loads one mission
          session (or explicitly separate sessions), mints TSK_*, assigns
          WorkerWriteScope, emits SessionHandoff, spawns workers via
          AsyncTaskDispatch, then MUST end the turn (EvEndCoordinatorTurn).
          Worker completion SHALL be host-driven EvWorkerReturn / async
          revival on a later coordinator turn — NOT a blocking await on the
          spawn turn. Parallel waves SHALL obey MN-REQ-12.5 (disjoint
          anchors or separate sessions; MUST NOT overlapping dual-write).
          When session ACL is enabled, the shipped CapsPolicy ACL
          hard-rejects mutate outside WorkerWriteScope. RSV lease
          (MN-REQ-12.13) sits under Commit — not a third operator.
        */
        attribute requirementId : String = "MN-REQ-12.12";
      }
    }

    // ----- 0.5 Recall / Commit (math skeleton; engine cut not this PR) -----

    requirement def MN_REQ_13_RecallCommit {
      doc /*
        Group (thin 0.5): agent surface is two operators only — Recall(q)
        and Commit(Δ) — over session graph S with rate cap R. Grammar SSOT:
        docs/grammar/math-skeleton.md. Does not replace MN-REQ-02.4 / 04.*.
        Engine/MCP cut SHALL NOT be claimed from this group alone.
      */
      attribute requirementId : String = "MN-REQ-13";

      requirement def MN_REQ_13_1_TwoOperators {
        doc /*
          SHALL model exactly two product operators: Recall(q) (seed then
          bounded k-hop reconstruct; empty q ⇒ session outline census of
          S — leftover empty-seed skip is leftover, not TARGET) and Commit(Δ)
          (one gate; mutate / ingest / ImportAbsorb / SameThingAbsorb are
          Commit rules — absorb is a rule family, not extra operators). RSV SHALL
          be a lease under Commit / SessionLifecycle, not a third API.
          HostSearchBridge SHALL remain outside MemNetSystem. Layer / Tier A
          remain REJECTED on accept (retire-from-wheel leftover; hierarchical
          reconstruct is not Layer dialect). PinMapShapedRead implemented
          SHALL NOT be read as BoundedMatchFind shipped (#73).
          Goldfish SHALL be Shape: the LLM SHALL NOT receive raw session S
          (pin_map depth/row/fan-out caps; hide recycled). Goldfish SHALL
          interact only with relevant slices. Prefer one pin_map on the
          live TSK (HiAgent current subgoal).           Extra topics: at most one view=shell survey, then interior on
          the task — SHALL NOT default to N serial full maps (duplicate
          LAW / overlap). view=shell is not session outline (MN-REQ-04.9). Seed set |Q|≤L
          SHALL union k-hop under one M (not Path-B M×anchors). Goldfish
          SHALL emit a sparse Δ (CREATE/SET; leftover NEW sugar allowed
          on 0.9; SHALL NOT echo the fetched slice); the session SHALL take
          it via Commit. SHALL NOT call that
          writeback Absorb (ImportAbsorb remains Path-B WorkingMemorySlice +
          leftover id_policy only — not entity resolution). SameThingAbsorb
          is a distinct in-session Commit rule, not goldfish-writeback naming
          and not ImportAbsorb. Host Snap (corpus locators via RagHostHook) SHALL
          stay outside MemNetSystem and SHALL NOT ANN-index the session.
          In-session task already on S SHALL RelativeSeed MATCH_L then
          ShapeWalk (leftover read_list / copy-id --anchor named leftover)
          — not Snap-on-session. Switch-task SHALL
          settle the old TSK then Shape a new ego — not Peak_L as default.
          SHALL NOT: rag_query; embeddings; PPR; RRF; GST/Steiner; ANN on
          the session; free MATCH/RETURN as goldfish; new HostSearchBridge
          leaves or HIT/RagDecision envelopes; dual-teach GraphQL /
          LangChain / HiGram as agent wire.
        */
        attribute requirementId : String = "MN-REQ-13.1";
      }

      requirement def MN_REQ_13_2_SameThingAbsorb {
        doc /*
          Second absorb case under Commit, distinct from ImportAbsorb.
          SameThingAbsorb SHALL collapse two live session elements only
          when the agent judges they are one world-thing. It is a Commit
          rule, not a product verb, not Recall, not RelativeSeed /
          ShapeWalk / pin_map. Pattern match is labels + properties (and
          relationship type + ends); SHALL NOT leftover MERGE-by-id /
          store-key / elementId. Same name (or any shared cue) is a
          candidate only. Two same-name nodes that are different
          world-things SHALL remain two (two "First National Bank"s stay
          two) and SHALL appear on Recall as CueConflict (two roots), not
          as one merged node. Collapse SHALL wait until the agent has
          seen that conflict on find / pin_map emit. Name is a handle, not the thing: a name-change SHALL NOT
          mint a second thing-node; optional aka (or name tokens pointing
          at one element) is enough; name-token history is optional.
          CHANGED between two thing-nodes only if the world actually split.
          ImportAbsorb SHALL remain Path-B WorkingMemorySlice + leftover
          id_policy and SHALL NOT do this entity resolution. Goldfish
          writeback SHALL still not be called Absorb (MN-REQ-13.1).
          operatorCount stays 2.
        */
        attribute requirementId : String = "MN-REQ-13.2";
      }
    }

    // ----- Atelier-board asks (14.1, 14.3, 14.4, 14.9-14.13 implemented; 14.2 PARKED; 14.5-14.8 PROPOSAL, target only) -----

    requirement def MN_REQ_14_AtelierBoardAsks {
      doc /*
        Group (PROPOSAL, 2026-11-02, owner ask "Model the new feature";
        requests from Atelier Keeper). Source: platform-plan
        MODEL-AND-PERF.md and bench/memnet-engine.py (synthetic board of 61
        rows per symphony; measured in-process at origin/master bb4a4dc,
        0.20.2). Nine leaves, 14.1 to 14.9, plus a tenth, the per-session
        total-bytes cap (14.10), block MemNet as an Atelier board store.
        An eleventh (14.11) makes the write paths that bypass the mutate
        gate enforce the same caps. A twelfth (14.12) makes the byte-budget
        check incremental. A thirteenth (14.13) pages find and typed walks
        by an opaque cursor.
        Implemented with runtime tests: leaves 14.1, 14.3, 14.4 and 14.9 to
        14.13 (test files named in each leaf's doc). The rest are target
        only: leaves 14.5 to 14.8 are PROPOSAL, and leaf 14.2 is PARKED
        until Elon reviews it (scope note r00002195). Leaf 14.3 was
        un-parked by owner issue #247 (items 1-3) and built. A target-only
        leaf is never counted as verified. Defects found on the way are
        recorded in MN-VER-14-D01 and MN-VER-14-D02, not as requirements.
        Line refs in 14.1, 14.4 and 14.6 are at the #245 head (gql.py:388
        and the 14.3 refs are at the typed-walks head); other refs below
        are at bb4a4dc, parts/common/memnet/memnet/.
      */
      attribute requirementId : String = "MN-REQ-14";

      requirement def MN_REQ_14_1_WhereRangeComparison {
        doc /*
          Status: implemented (owner's rules). Before this cut a WHERE with
          < > <= >= was refused unsupported_predicate (measured on ee36a95
          and bb4a4dc). Rules: (1) < > <= >= SHALL be honoured in a node
          WHERE (also inline, MATCH (n:T WHERE ...)) and in a relationship
          WHERE, for WHERE ... SET and WHERE ... DELETE (MN-REQ-03.4;
          gql.py:282-319). A node WHERE that matches no record is refused
          not_found, more than one cue_conflict; a relationship WHERE ...
          SET updates every match. A relationship WHERE ... DELETE is now
          honoured (RelDropRec, gql.py:132; mutate_gate.py:996-1050): if it
          matches no relationship it is refused not_found, if it matches
          more than one it is refused cue_conflict, and nothing is deleted;
          its WHERE takes predicates on the relationship only (a.* or b.*
          is refused unsupported_predicate). (2) The left side is a
          property; the right operand is a number literal or a quoted
          string; any other right operand (a property, a $param, a boolean
          or null, a bare word) or a literal on the left is refused
          unsupported_predicate. (3) Ids are opaque identity: no meaning
          comes from an id's value, order or sequence. A range comparison
          on the id property of a node or relationship (n.id, r.id) is
          refused unsupported_predicate at parse time, number or string
          operand, bare or under AND / OR / NOT, with nothing written
          (gql.py:287-289). Equality on id keeps working through the
          nickname index (14.4). (4) A stored field counts as numeric iff
          it fully reads as a number (exponent allowed). Number compares
          with number, string with string by code point (for UTF-8 the same
          as byte order), with no locale collation. A non-finite numeric
          field (for example 1e999, which overflows to inf) never matches a
          number range (gql.py:388); NaN does not read as a number
          (gql.py:145), so it is a non-numeric value under rule (5). (5) Type
          refusal (owner go 2026-11-04; replaces the #250 rule that a mixed
          pair silently does not match; code refs at d64bedf). A quoted
          operand whose text fully reads as a number ('123', '000123',
          '-2.5', '1e3') is refused at parse time, whatever the data, with
          @ERR: where_type_mismatch|WHERE <op> on <var>.<key>: quoted number
          '<lit>'; use a number literal (gql.py:306-319); the id check of
          rule (3) runs first, so n.id > '5' stays unsupported_predicate,
          and '' or ' 5' do not read as numbers and stay strings. A quoted
          (non-numeric) string operand against a stored value that reads as
          a number (rule (4), non-finite included, for example '5' or
          '1e999') is refused when evaluated with @ERR:
          where_type_mismatch|WHERE <op> on <var>.<key>: stored number vs
          quoted string; use a number literal (gql.py:394-401); <op> is the
          operator as written. AND and OR evaluate every child before
          combining (gql.py:347-356), so the refusal does not depend on
          sibling order, and one numeric row refuses the whole statement.
          The refusal is exit 1 like other WHERE refusals and covers node
          and relationship WHERE, SET and DELETE, inline WHERE and query
          typed-walk --where (an inline WHERE refusal is not retried as a
          relationship MATCH, gql.py:993-996). Kept as no match, not an
          error: a missing property or an empty value; a number literal
          against a non-numeric value ('abc', '-', 'NaN', ' 5'); a
          non-finite numeric field against a number literal. Equality is
          unchanged: = <> != are exact text, so n.rowRev = 124 does not
          match '000124'. (6) WHERE is three-valued
          (gql.py:321-399): a comparison on a missing or empty property, a
          number literal against a non-numeric value or a non-finite
          numeric field is UNKNOWN (so a non-finite field still matches
          through a true OR sibling, and never under AND), AND / OR / NOT
          carry UNKNOWN, and UNKNOWN is no match, so NOT over a no-match
          stays no match; a where_type_mismatch refusal is not UNKNOWN, it
          refuses the statement, under NOT too. (7) On any refusal nothing is written, so there
          is no partial write. (8) Agent MATCH ... RETURN stays
          product-gated (gql_parse_front.py:34; paged reads are 14.2), so
          the board wake read is not opened by this leaf. rowRev: a stored
          rowRev such as '000124' fully reads as a number, so it is numeric
          under rule (4); compare it with a number literal (n.rowRev > 123).
          A quoted operand (n.rowRev > '000123') is refused
          where_type_mismatch under rule (5). Evidence: tests/test_range_where.py,
          tests/test_id_opaque_range.py, tests/test_range_where_nonfinite_or.py,
          tests/test_range_type_refusal.py,
          tests/test_typed_walk_where.py::test_main_use_row_rev_number_operand,
          ::test_main_use_row_rev_quoted_operand_is_refused.
          Verify: MN-VER-14-S01. Behaviour: BoardWakeRead, RangeWhereCompare.
        */
        attribute requirementId : String = "MN-REQ-14.1";
      }

      requirement def MN_REQ_14_2_PagedReadsPastCap {
        doc /*
          Status: PROPOSAL, PARKED for Elon's review (scope note r00002195);
          not accepted. Today a read returns at most 50 rows (config.py:71)
          and agent RETURN is forbidden (gql_parse_front.py:34, product
          gate). Proposed: a read past the cap SHALL be reachable by a
          cursor (opaque, session-bound) or by a since-filter (14.1) so the
          caller resumes without a gap or repeat while the session is
          unchanged. The cap itself stays; the page size never exceeds it.
          Paging is preferred over opening agent RETURN. Open questions in
          the PR body.
          NOTE (Elon CTO review, not a rewrite of this leaf): his call is a
          since-filter, keyset paging on 14.1, and no opaque cursor for now.
          It keeps no server state, has no cursor lifetime, and survives
          evict and restore (MN-REQ-05.5). It needs two things only: the
          engine orders by the filter key, and each reply carries a
          more-rows flag when it hit the cap. The key must be unique and
          only increase: rowRev unique per board must be stated; real ids
          cannot break ties because agents never see them (14.7). If this
          leaf is unparked, 14.2 and S02 are rewritten to that shape.
          Verify: MN-VER-14-S02 (shape only until accepted). Behaviour:
          BoardWakeRead.
        */
        attribute requirementId : String = "MN-REQ-14.2";
      }

      requirement def MN_REQ_14_3_TypedDirectedWalks {
        doc /*
          Status: implemented (owner issue #247 items 1-3; paging stays
          14.2). Un-parked by the owner's ask; the in-run architect decided
          the shape (skill v3.10.0). The earlier proposal (type and direction
          arguments on neighbors / the leftover query_walk) is superseded and
          not built. Line refs at the typed-walks head,
          parts/common/memnet/memnet/.
          (1) Surface. A read verb, not GQL: memnet query typed-walk --from
          <id> --type <T> [--dir out|in|both] [--min-hops N] [--max-hops N]
          [--where "<pred on n>"] [--limit N] [--session S] [--caller C]
          (cli.py:1948-2000), defaults dir out, hops 1..1, limit 50; read
          ACL as pin_map (cli.py:1983), run under the session lock. Engine
          for in-process callers: typed_walk.typed_walk(store, ...)
          (typed_walk.py:103-196). Products reach the verb through serve and
          the product gateway (MN-REQ-06.12), argv unchanged. There is no
          MCP tool: an MCP reply must not carry real ids, and the reply rows
          are ids, so MCP exposure waits for the 14.7 handles. Agent MATCH
          ... RETURN stays product-gated (gql_parse_front.py:34). The
          leftover query walk, the MCP query_walk tool, MemStore.neighbors
          and context_walk_hops are unchanged.
          (2) Fold. --type goes through config.normalize_relation
          (config.py:51-54): an invalid name is refused invalid_relation,
          then all-upper snake folds to lowerCamel (PART_OF -> partOf,
          IN_SESSION -> inSession) and any other valid name only has a
          leading capital lowered (PartOf -> partOf). part_of is not folded
          and does not match partOf. Stored edges are indexed under their
          standard spelling, so a legacy raw spelling still matches. A
          valid type with no edges returns 0 rows. The reply header echoes
          the folded type.
          (3) Semantics. --from is a nickname id resolved through the id
          index (match_nickname, EDG rows excluded; typed_walk.py:94-100):
          empty is refused no_anchor, 0 hits not_found, more than 1
          cue_conflict. Hids are never accepted or emitted. Traversal is BFS
          on one edge type in direction out, in or both: each node reached
          at hop d with min <= d <= max is one row carrying the first
          shortest path to it. A node is reached at most once and the start
          never, so cycles end, a self-loop gives no row and parallel edges
          give one row (the first edge). Nodes below min-hops are expanded
          but not emitted. An edge whose far end is not stored is skipped
          but counted as examined. All-paths enumeration is not offered.
          (4) WHERE. --where is a predicate on n, the row's end node,
          parsed by gql.parse_where_clause (gql.py:153) and evaluated by
          gql.eval_where (gql.py:321) with the MN-REQ-14.1 rules unchanged:
          three-valued, a missing, empty or non-finite field, or a number
          literal against a non-numeric value, is UNKNOWN and UNKNOWN is no
          match; a quoted number, or a quoted string against a stored
          number, is refused where_type_mismatch; a range on n.id is refused
          unsupported_predicate (equality on n.id works); a variable other
          than n is refused unsupported_predicate. WHERE filters rows, not
          traversal. rowRev: compare with a number literal
          (--where "n.rowRev > 123" matches rowRev '000124'); a quoted
          operand (n.rowRev > '000123') is refused where_type_mismatch.
          (5) Order (walk-only). Rows go in hop order; within a hop, in the
          parents' BFS order; for each parent, its type-T edges in edge
          first-insert sequence (RecordTable _seq; for both, out and in
          merged by that sequence; mem_store.py:205-224). No id value, id
          order or id sequence, no hid and no property value feeds the
          order. It survives an id rename, snapshot save / load, checkpoint
          restore and a refused mutate batch (the rollback is order-exact,
          see (7)). A truncated reply is a prefix of the untruncated order.
          pin_map's Recall Shape order is a different rule and is unchanged.
          (6) Bounds (typed_walk.py:28-33, read at call time; checks
          :115-127). Hops 1 <= min <= max <= 10, else refused
          hops_out_of_range. Direction out, in or both, else refused
          invalid_direction. Limit 1..500 (default 50), else refused
          limit_out_of_range; a full page with one more qualifying row sets
          truncated limit, exactly limit rows with the walk exhausted sets
          none. At most 20,000 typed edge reads per call; past it the walk
          stops and returns the rows so far with truncated budget (this one
          budget bounds visited and frontier). Reply at most 1,048,576
          UTF-8 bytes (lines plus newlines, header and stats included):
          emit_walk stops before the row that would pass it, flag bytes
          (typed_walk.py:240-263). The first bound hit wins.
          (7) Index. An adjacency index (node hid, standard relation, out |
          in) -> edge hids lives inside RecordTable (mem_store.py:34-57,
          kept in _index :75-83 and _unindex_adj :85-97), with an indexed
          (src, dist, relation) snapshot per edge for unindexing; every dict
          mutator keeps it, MemStore._index_edge re-reads the row so an
          in-place endpoint edit reaches it (mem_store.py:781-790), and
          verify_indexes() reports "adjacency index differs" on a mismatch
          (mem_store.py:689-699). A hop reads only the type-T bucket(s)
          (MemStore.typed_edges, mem_store.py:609-617), never other edges;
          WalkResult.examined counts those reads. It is never written to a
          snapshot and is rebuilt on load. A refused mutate batch is rolled
          back order-exact: deletes are journalled (mutate_gate.py:608) and
          restored under their first-insert seq and write_order index
          (mutate_gate.py:723-761; mem_store.py:450-499 and
          RecordTable.restore :226-245; the legacy add / update path
          restores live rows in place, mutate_gate.py:1241), so write_order,
          RecordTable order, walk output and snapshot text equal the state
          before the batch.
          (8) Reply (typed_walk.py:199-263). One line each:
          @WALK: type=<folded>|dir=<d>|hops=<min>..<max>|limit=<n>; then
          @PATH: <row>|<hops>|<shaped path> per row (start and intermediate
          nodes kind + id only, the END node with all its properties, edges
          -[:<type> {id:'E1'}]-> forward or <-[:<type> {id:'E1'}]- backward;
          a node or edge without a nickname shows no id); then
          @STAT: walk_rows|<rows>|<limit>, @STAT: walk_truncated|none, limit,
          budget or bytes|- and @STAT: walk_cursor|-|-. walk_cursor (and
          WalkResult.cursor, always None) is the reserved slot for paging
          (14.2, issue #247 item 4); no other line changes then.
          Evidence: tests/test_typed_walk.py, tests/test_typed_walk_where.py,
          tests/test_walk_index.py, tests/test_typed_walk_perf.py.
          Verify: MN-VER-14-S03. Behaviour: TypedWalk.
        */
        attribute requirementId : String = "MN-REQ-14.3";
      }

      requirement def MN_REQ_14_4_IdIndexAndLinearLoad {
        doc /*
          Status: implemented. Before this cut id lookup scanned every
          record (match_nickname; no nickname index) at 1.2-1.7 ms for 31k
          records, and session load built a hid set per edge end
          (load_records), quadratic: 31k records took 34.9 s snapshot load
          (both measured on bb4a4dc). The "id" looked up is the nickname
          fields['id'] (match_nickname), not the store key (hid). MemStore
          SHALL keep a nickname index (nickname -> hids, so duplicate
          nicknames stay allowed); as built it is RecordTable
          (mem_store.py:34), the store's hid -> record dict, which updates
          the index on every write, rollback included, and is never stored
          in the snapshot. Lookups through the index (match_nickname,
          resolve_one, match_nodes by id, find by id locator;
          mem_store.py:423, :512, :523, pin_map_composer.py:494-512) SHALL
          return the same rows in the same order as the scan did. A
          snapshot SHALL load in time linear in records (load_records,
          mem_store.py:205-232). Bounds (tests/test_id_index_perf.py): a
          nickname lookup or resolve_one takes at most 0.02 ms at 5,000
          rows; loading 8,000 rows takes at most 8 x the 2,000-row time.
          The index serves equality lookup only; no range or order is
          read from an id (14.1 rule 3). Index and load SHALL NOT change what a read
          returns and SHALL survive evict and restore (MN-REQ-05.5). The
          real-id key of MN-REQ-14.6 stays target only. 14.4 lands before
          14.5. Evidence: tests/test_id_index.py, tests/test_id_index_perf.py.
          Verify: MN-VER-14-S04. Behaviour: SessionLoadLinear.
        */
        attribute requirementId : String = "MN-REQ-14.4";
      }

      requirement def MN_REQ_14_5_RaisableSessionRecordCap {
        doc /*
          Status: PROPOSAL; DEPENDS ON MN-REQ-14.4. A session holds at most
          5,000 records, nodes plus edges (config.py:125, mem_store.py:
          267-272), about 25 symphonies of 195 records; load at 7.8k / 31k
          records is refused rows|5001/5000. The cap SHALL be raisable by
          the operator as a process-wide environment setting, not per
          session (default 5,000, unchanged) only once 14.4 lands: raising
          it before then runs into quadratic load. The raised cap SHALL
          apply the same way to mutate, import and snapshot load (one
          helper, as MN-REQ-05.3 / 05.4). Tombstones (14.6) do not count
          against this cap. Raising it multiplies the memory bound of 14.9;
          the per-session total-bytes cap (MN-REQ-14.10) bounds that.
          Verify: MN-VER-14-S05. Behaviour: SessionLoadLinear.
        */
        attribute requirementId : String = "MN-REQ-14.5";
      }

      requirement def MN_REQ_14_6_IdDesign {
        doc /*
          Status: PROPOSAL, target only; traced to MN-REQ-14.4 (the id index
          enforces it) and to MN-REQ-02.8 (id not required on the wire) and
          MN-REQ-02.9 (no cousin store key). Note gql-wire-profile.md:58:
          CREATE / MERGE have no store-key production; a real id is minted
          by the engine and is never written by the caller, so it is not a
          store-key production. (1) The engine mints an id at write time as
          a UUIDv7 (RFC 9562), with no saved counter and no pool. A UUIDv7
          is unique with high probability through its random bits; it is
          not unique by construction, and the clock can go backwards after
          a crash or restore. The real guarantee is (4). Pin-ingested
          elements are created by Commit and get a minted UUIDv7 like any
          write; their locators stay properties, not identity and not a
          store key (pinIngestDeterministicIdsReq, MN-REQ-11.16).
          (2) Ids are never reused or changed: a deleted id is retired
          forever (tombstoned), because outside references (rows, links,
          logs, other products) may still hold it. A lookup of a deleted id
          SHALL return a clear "deleted" result, never not_found and never
          a different record. Tombstones are id-only entries (the id and a
          deleted marker) in the id index and in the snapshot, not full
          records. They do NOT count against the record cap (14.5); once they
          exist they SHALL count toward the per-session total-bytes cap
          (14.10; no tombstones exist today). A legacy
          snapshot loads with an empty tombstone set. (3) Save, load and
          restore SHALL NOT mint or rewrite ids (existing owner rule);
          id-less legacy links stay id-less. (4) The id index SHALL refuse
          a write whose id is a duplicate of an existing or tombstoned id.
          INTERIM NOTE (as built, not this target): an id is opaque
          identity only; no meaning comes from its value, order or
          sequence, and none is promised. The engine guarantees only that
          an engine-minted nickname id is unique among live rows and is
          never minted again, even after a delete or a refused batch (a
          refused batch's ids are burnt), across snapshot save / load and
          checkpoint restore. For that alone the store keeps a per-prefix
          high-water that is never lowered, clear() included
          (mem_store.py:127-133), persisted as a snapshot "#@IDHW:" line
          (snapshot.py:393-438); #@IDHW serves never-reuse only. Evidence:
          tests/test_id_index.py (test_mint_* cases). UUIDv7 and
          tombstones stay target only.
          Verify: MN-VER-14-S06. Behaviour: IdMintAndRetire, IdLifecycle.
        */
        attribute requirementId : String = "MN-REQ-14.6";
      }

      requirement def MN_REQ_14_7_AgentHandlesNotIds {
        doc /*
          Status: PROPOSAL, target only; traced to MN-REQ-14.6 and to the
          owner decision of 2026-11-02 (handles only for the LLM MCP
          surface; real ids on a developer surface, 14.8). On the MCP
          surface agents get handles only; the engine maps each handle back
          to the real id. No reply of any MCP tool SHALL carry a real id:
          find, read, walk, error text, and also pin_map, export_pin_map,
          snap_model, import_slice, session_save and session_load. Handle
          lifetime: a handle is process-unique (never reused within the
          process) or carries its session, and is persisted in its session's
          snapshot; it stays valid across evict, restore, save and load. A
          handle from another session is foreign and SHALL be refused
          (stale/foreign), never resolved. A handle that does not match (bad, stale or of
          a deleted record) SHALL be refused with a clear error, never a
          different record. Real ids stay internal to the engine and its
          snapshots. Migration note: this changes MCP reply contracts;
          existing MCP reply verify cases, for example MN-VER-07-S01, are
          re-read against it before a cut. Verify: MN-VER-14-S07.
          Behaviour: HandleResolve.
        */
        attribute requirementId : String = "MN-REQ-14.7";
      }

      requirement def MN_REQ_14_8_DeveloperSurfaceRealIds {
        doc /*
          Status: PROPOSAL, target only; traced to MN-REQ-14.6. Owner
          refinement: a separate developer / tool-integration interface,
          for other tools and products built on MemNet, SHALL return real
          ids. They are stable (never reused or changed, MN-REQ-14.6) and
          usable as outside references. A lookup of a deleted real id
          returns "deleted" on this surface too. The surface is a separate
          listener or transport with its own credential, never a flag on the
          MCP endpoint (an agent can set a flag). A caller without the
          developer credential is refused. Whether it is enabled by default
          is open. Verify: MN-VER-14-S08. Behaviour: DeveloperIdLookup.
        */
        attribute requirementId : String = "MN-REQ-14.8";
      }

      requirement def MN_REQ_14_9_ValueCap32k {
        doc /*
          Status: implemented (tests/test_value_cap_32k.py,
          tests/test_line_cap_whole_line.py, tests/test_line_cap_edge_schema.py);
          FLAGGED FOR ELON. The per-value cap
          (MEMNET_MAX_VALUE_BYTES, config.py:130) rises from 4,096 to
          32,768 bytes, one global value, no chunking, still overridable by
          env, because Atelier rows hold up to 8,000 characters, which is up
          to 32,000 bytes in UTF-8 (4 bytes per character). That is 768
          bytes under the cap, and holds only if the stored value is the
          raw row text, with no envelope and no JSON escaping. Values up to
          32,768 bytes SHALL be accepted; larger values SHALL be refused
          with a clear error; the cap is counted in bytes. Snapshots written
          under the old cap SHALL still load. LINE CAP: a 32,768-byte value
          could not fit the old 32,768-byte line cap (MEMNET_MAX_LINE_BYTES,
          config.py:131; the cap is now 135,168), because backslash and pipe are written twice
          (docs/cap-contract.md:153-158 says a single value always fits a
          line, and caps a product raise at 16,384). 14.9 SHALL therefore
          also raise the default line cap (fixed interface, owner
          t1443s8385) to 4 x 32,768 + 4,096 = 135,168 bytes. Arithmetic:
          the worst-case wire escape is 4x, not 2x: \x1c, \x1d and \x1e
          each become 4 bytes (wire.py _SPLITLINES_ESC), while pipe and
          backslash double; so a 32,768-byte value escapes to at most
          4 x 32,768 = 131,072 bytes, plus 4,096 bytes for tag, field names,
          separators and the other fields of the line = 135,168; still
          overridable by env. Mutate-time refusal: before storing, mutate SHALL
          compute the escaped wire size of the whole record line as it
          would be saved (all fields: tag, field names, separators and every
          value, after the write) and, if it exceeds the line cap, refuse
          limit_exceeded, message line_bytes|{n}/{max}, with nothing
          stored. The real cap applies to the whole physical line
          (tag_map.py:291-298), so checking one value is not enough: a
          record whose fields each fit can still exceed the cap in total.
          With the whole-line check no accepted write makes a snapshot
          unsaveable, and a later change to the escape table cannot break
          saving. The value-cap message stays value_bytes|{n}/{max}. The
          cap-contract.md lines 153-158 change in the code PR (code PR
          fix/line-cap-whole-line for the whole-line check). IMPACT: at one
          capped value per record, values grow from 5,000 x 4,096 bytes
          (19.53 MiB) to 5,000 x 32,768 = 163,840,000 bytes (156.25 MiB),
          8 times as much. The per-record bound is the line cap: a record is
          at most 135,168 bytes on the wire, whatever its field count, so
          records x line cap is 5,000 x 135,168 = 675,840,000 bytes
          (644.53 MiB), and the per-session total-bytes cap (MN-REQ-14.10)
          is the bound that counts. Snapshot size, save and load time, and pin_map read size
          all grow with value size. Verify: MN-VER-14-S09. Behaviour:
          ValueLineCapEnforce.
        */
        attribute requirementId : String = "MN-REQ-14.9";
      }

      requirement def MN_REQ_14_10_SessionTotalBytesCap {
        doc /*
          Status: implemented (mutate gate, snapshot load and save, snapshot
          import, durable hydrate; ingest through the mutate gate; tests
          tests/test_session_bytes_budget.py and
          tests/test_bypass_paths_caps.py). Without a total
          the record cap (14.5) and the value cap (14.9) multiply each
          other, and the session-count cap (MN-REQ-05.5) multiplies that
          again across the process. SHALL cap the total bytes held by one
          session, counted as escaped snapshot line bytes (UTF-8) of every
          SCHEMA, record and edge line. A write that
          would go over it is refused with a named code, limit_exceeded|
          session_bytes {n}/{max}, and writes nothing. The same check runs
          on snapshot load, snapshot save, snapshot import, durable hydrate
          and ingest (via the mutate gate); a delete never trips it. The
          setting is the env var MEMNET_MAX_SESSION_BYTES. Its default is
          163,840,000 bytes (5,000 x 32,768 = 163,840,000; 156.25 MiB; owner-set; one
          named constant, DEFAULT_MAX_SESSION_BYTES in config.py). It is a
          deliberate cap, not a floor: 5,000 records at the 135,168-byte
          line cap would be 675,840,000 bytes, so the default can refuse a
          write that the value and line caps allow, and a lower setting can
          refuse to load or hydrate a session that is over it (the setting to
          raise is named in the error). Linked from 14.5 and
          14.9. The total is kept incrementally (MN-REQ-14.12).
          Verify: MN-VER-14-S10; incremental total: MN-VER-14-S12. Behaviour: ValueLineCapEnforce, SessionByteBudgetStates, BypassPathCapEnforce.
        */
        attribute requirementId : String = "MN-REQ-14.10";
      }

      requirement def MN_REQ_14_11_BypassPathCaps {
        doc /*
          Status: implemented (tests/test_bypass_paths_caps.py). A write
          path that does not go through the mutate gate SHALL enforce the
          same caps as mutate, with the same limit_exceeded codes
          (value_bytes|{n}/{max}, line_bytes|{n}/{max},
          session_bytes|{n}/{max}) and SHALL be atomic: a refused call
          leaves the session exactly as it was. Paths: snapshot import
          (import_absorb), durable hydrate (durable/sync.py), CLI delete and
          housekeep prune. Hydrate into a session already over its byte
          budget (for example under a lower MEMNET_MAX_SESSION_BYTES) is
          refused session_bytes with nothing loaded; durable data is never
          touched or truncated. A delete shrinks the session, so the byte
          budget never refuses it, but the edge and SCHEMA lines it rewrites
          (an edge to a deleted node is written with the endpoint handle)
          must still pass the line cap, else the delete is refused and
          nothing is removed. Snapshot load keeps its loader refusal of an
          over-cap value or line and also refuses a session over budget;
          save refuses an over-budget session and writes no file. The
          field cap (MN-REQ-05.4) also applies on these paths: the bypass
          guard runs it before the line cap, and a record over the field
          cap (MEMNET_MAX_FIELDS, default 64) is refused limit_exceeded
          fields|{n}/{max} with nothing written.
          Verify: MN-VER-14-S11. Behaviour: BypassPathCapEnforce.
        */
        attribute requirementId : String = "MN-REQ-14.11";
      }

      requirement def MN_REQ_14_12_IncrementalByteBudget {
        doc /*
          Status: implemented (this PR). The budget check is incremental:
          it re-encodes only what changed, total equal to a full recount.
          The session total of 14.10 SHALL be kept as a per-session running
          sum of escaped UTF-8 line bytes, updated on create, update,
          delete, import, hydrate and load. The rows re-encoded per write
          SHALL be the changed nodes plus the incident edges of changed
          nodes; only the first check after load or hydrate, a store swap
          (MemStore replaced), a SCHEMA change, a bypass_guard rollback, a
          row-count tripwire or a leftover-nick collision pays one full
          rebuild. The ledger is dropped on expire and on save-on-expire
          (it lives on the registry entry) and is rebuilt on the next load.
          The
          running total SHALL equal a full recount of the SCHEMA and record
          lines at every point; the debug flag MEMNET_DEBUG_SESSION_BYTES=1
          makes every check also recount and assert equality. Widening a
          tag's SCHEMA by an undeclared key, renaming a node (edge lines
          carry the endpoint nicks) and relation folding are accounted
          exactly. A bypass_guard rollback invalidates the ledger, so the
          next check rebuilds it from the restored store and the total again
          equals a full recount; a failure inside the sync also invalidates
          it. The refusal text stays session_bytes|{total}/{budget}, where
          {total} is the partial sum in write order (the refusal path
          recomputes with the full walk). wire.join_payload escaping is
          table based (str.translate) and byte-identical to the former
          per-character loop; no complexity bound is claimed for
          join_payload. Semantics of 14.10 and 14.11 (default
          163,840,000 bytes, codes, atomicity) are unchanged.
          Verify: MN-VER-14-S12. Behaviour: SessionByteBudgetStates.
        */
        attribute requirementId : String = "MN-REQ-14.12";
      }

      requirement def MN_REQ_14_13_PagingCursor {
        doc /*
          Status: implemented (owner issue #247 item 4). Cursor paging for
          find (query find, MCP find) and typed walks (query typed-walk, MCP
          typed_walk); serve proxies the same argv. It does not open agent
          RETURN and does not un-park 14.2, the general read past the 50-row
          cap (see the Elon NOTE on 14.2: his call for that leaf is a
          since-filter; the owner asked for a cursor on these two verbs).
          Request: limit (walk 1..500 as 14.3; find as before) and an
          optional cursor. Reply: the next cursor while rows remain, else
          none. CLI walk: walk_cursor stat; CLI find: a last line
          "@STAT: find_cursor|<token>|-" ("-" when none); MCP typed_walk:
          next_cursor (also stats.cursor), absent when paging was not asked,
          null when no more; MCP find: the same stat line in its stdout.
          Token. Opaque: "c_" plus base32 of a payload and a MAC. The payload
          holds a format version, the query kind, the resume position (a row
          count into the result, never an id or id order), the store
          change_count (mem_store.py change_count) and a fingerprint of the
          query parameters; the MAC is HMAC-SHA256 under the session id.
          Callers never compare tokens; none is built or read by hand.
          Refusals, in this order: bad_cursor (not a token, forged, issued
          by another session or for the other verb); cursor_mismatch (a
          query parameter changed; limit is not one and may change between
          pages); stale_cursor (change_count differs: any write since the
          page; reads never bump it). The cursor resumes by re-running the
          query and skipping the rows already given, so pages join without
          a gap or repeat while the session is unchanged. A walk page cut by
          the reply-byte cap (14.3) still returns a cursor at the first
          dropped row; a page cut by the 20,000 edge-read budget returns
          none (a re-run would hit the same budget). Ranks, hop order and
          first-insert order are those of 14.3; no id value or hid sets any
          order.
          Back-compat. Paging is opt-in: walk by an explicit limit or a
          cursor, find by --paged or a cursor. A request that asks for none
          of these gets the reply bytes it got before (tests pin them).
          Evidence: tests/test_paging_cursor.py.
          Verify: MN-VER-14-S13. Behaviour: PagedRead.
        */
        attribute requirementId : String = "MN-REQ-14.13";
      }
    }
  }

  // --- Requirement usages + #derivation (SysML v2 deriveReqt) ---
  // Ends must be requirement *usages*; defs stay nested for structure.

  requirement missionReq : MN_REQ_00_MissionBridge;

  requirement sessionLifecycleReq
    : MN_REQ_00_MissionBridge::MN_REQ_01_SessionLifecycle;
  requirement namedSessionsReq
    : MN_REQ_00_MissionBridge::MN_REQ_01_SessionLifecycle::MN_REQ_01_1_NamedSessions;
  requirement sessionLifecycleOpsReq
    : MN_REQ_00_MissionBridge::MN_REQ_01_SessionLifecycle::MN_REQ_01_2_SessionLifecycleOps;
  requirement sessionTtlAndCapsReq
    : MN_REQ_00_MissionBridge::MN_REQ_01_SessionLifecycle::MN_REQ_01_3_SessionTtlAndCaps;
  requirement saveSessionSnapshotReq
    : MN_REQ_00_MissionBridge::MN_REQ_01_SessionLifecycle::MN_REQ_01_4_SaveSessionSnapshot;
  requirement loadSessionSnapshotReq
    : MN_REQ_00_MissionBridge::MN_REQ_01_SessionLifecycle::MN_REQ_01_5_LoadSessionSnapshot;
  requirement optionalKeepSessionIdReq
    : MN_REQ_00_MissionBridge::MN_REQ_01_SessionLifecycle::MN_REQ_01_6_OptionalKeepSessionId;
  requirement sessionAsSsotHandleReq
    : MN_REQ_00_MissionBridge::MN_REQ_01_SessionLifecycle::MN_REQ_01_7_SessionAsSsotHandle;
  requirement noGraphDumpHandoffReq
    : MN_REQ_00_MissionBridge::MN_REQ_01_SessionLifecycle::MN_REQ_01_8_NoGraphDumpHandoff;
  requirement snapshotLosslessRoundTripReq
    : MN_REQ_00_MissionBridge::MN_REQ_01_SessionLifecycle::MN_REQ_01_9_SnapshotLosslessRoundTrip;
  requirement sessionLifecycleAclWhoReq
    : MN_REQ_00_MissionBridge::MN_REQ_01_SessionLifecycle::MN_REQ_01_10_SessionLifecycleAclWho;

  requirement memoryNetGraphReq
    : MN_REQ_00_MissionBridge::MN_REQ_02_MemoryNetGraph;
  requirement exactlyNodeAndEdgeReq
    : MN_REQ_00_MissionBridge::MN_REQ_02_MemoryNetGraph::MN_REQ_02_1_ExactlyNodeAndEdge;
  requirement nodesHoldAtomisedFactsReq
    : MN_REQ_00_MissionBridge::MN_REQ_02_MemoryNetGraph::MN_REQ_02_2_NodesHoldAtomisedFacts;
  requirement edgesAreFirstClassReq
    : MN_REQ_00_MissionBridge::MN_REQ_02_MemoryNetGraph::MN_REQ_02_3_EdgesAreFirstClass;
  requirement queryOverNodeEdgeGraphReq
    : MN_REQ_00_MissionBridge::MN_REQ_02_MemoryNetGraph::MN_REQ_02_4_QueryOverNodeEdgeGraph;
  requirement grammarExpressesNodeAndEdgeReq
    : MN_REQ_00_MissionBridge::MN_REQ_02_MemoryNetGraph::MN_REQ_02_5_GrammarExpressesNodeAndEdge;
  requirement parserRecoversNodeAndEdgeReq
    : MN_REQ_00_MissionBridge::MN_REQ_02_MemoryNetGraph::MN_REQ_02_6_ParserRecoversNodeAndEdge;
  requirement schemaValidatedIngestReq
    : MN_REQ_00_MissionBridge::MN_REQ_02_MemoryNetGraph::MN_REQ_02_7_SchemaValidatedIngest;
  requirement idNotRequiredOnWireReq
    : MN_REQ_00_MissionBridge::MN_REQ_02_MemoryNetGraph::MN_REQ_02_8_IdNotRequiredOnWire;
  requirement noCopyCousinStoreKeyReq
    : MN_REQ_00_MissionBridge::MN_REQ_02_MemoryNetGraph::MN_REQ_02_9_MustNotCopyCousinStoreKey;

  requirement strictMutateReq
    : MN_REQ_00_MissionBridge::MN_REQ_03_StrictMutate;
  requirement addFailsIfExistsReq
    : MN_REQ_00_MissionBridge::MN_REQ_03_StrictMutate::MN_REQ_03_1_AddFailsIfExists;
  requirement updateFailsIfAbsentReq
    : MN_REQ_00_MissionBridge::MN_REQ_03_StrictMutate::MN_REQ_03_2_UpdateFailsIfAbsent;
  requirement noSilentUpsertReq
    : MN_REQ_00_MissionBridge::MN_REQ_03_StrictMutate::MN_REQ_03_3_NoSilentUpsert;
  requirement honourWherePredicateReq
    : MN_REQ_00_MissionBridge::MN_REQ_03_StrictMutate::MN_REQ_03_4_HonourWherePredicate;

  requirement sliceEconomyReq
    : MN_REQ_00_MissionBridge::MN_REQ_04_SliceEconomy;
  requirement anchoredPinMapReq
    : MN_REQ_00_MissionBridge::MN_REQ_04_SliceEconomy::MN_REQ_04_1_AnchoredPinMap;
  requirement recycleHiddenFromPinMapReq
    : MN_REQ_00_MissionBridge::MN_REQ_04_SliceEconomy::MN_REQ_04_2_RecycleHiddenFromPinMap;
  requirement pinMapDepthAndRowCapsReq
    : MN_REQ_00_MissionBridge::MN_REQ_04_SliceEconomy::MN_REQ_04_3_PinMapDepthAndRowCaps;
  requirement engineLawPrependReq
    : MN_REQ_00_MissionBridge::MN_REQ_04_SliceEconomy::MN_REQ_04_4_EngineLawPrepend;
  requirement anchoredWalkReq
    : MN_REQ_00_MissionBridge::MN_REQ_04_SliceEconomy::MN_REQ_04_5_AnchoredWalk;
  requirement boundedMatchFindReq
    : MN_REQ_00_MissionBridge::MN_REQ_04_SliceEconomy::MN_REQ_04_6_BoundedMatchFind;
  requirement relativeSeedThenShapeWalkReq
    : MN_REQ_00_MissionBridge::MN_REQ_04_SliceEconomy::MN_REQ_04_7_RelativeSeedThenShapeWalk;
  requirement cueMultiRootHonestReq
    : MN_REQ_00_MissionBridge::MN_REQ_04_SliceEconomy::MN_REQ_04_8_CueMultiRootHonest;
  requirement sessionOutlineEmptyCueReq
    : MN_REQ_00_MissionBridge::MN_REQ_04_SliceEconomy::MN_REQ_04_9_SessionOutlineEmptyCue;
  requirement peakLLastResortReq
    : MN_REQ_00_MissionBridge::MN_REQ_04_SliceEconomy::MN_REQ_04_10_PeakLLastResort;
  requirement pinMapOrderFromObservablesReq
    : MN_REQ_00_MissionBridge::MN_REQ_04_SliceEconomy::MN_REQ_04_11_PinMapOrderFromObservables;
  requirement housekeepEndpointIdentityReq
    : MN_REQ_00_MissionBridge::MN_REQ_04_SliceEconomy::MN_REQ_04_12_HousekeepEndpointIdentity;

  requirement hardCapsReq
    : MN_REQ_00_MissionBridge::MN_REQ_05_HardCaps;
  requirement storeResourceCapsReq
    : MN_REQ_00_MissionBridge::MN_REQ_05_HardCaps::MN_REQ_05_1_StoreResourceCaps;
  requirement queryFanoutCapsReq
    : MN_REQ_00_MissionBridge::MN_REQ_05_HardCaps::MN_REQ_05_2_QueryFanoutCaps;
  requirement consistentValueByteCapReq
    : MN_REQ_00_MissionBridge::MN_REQ_05_HardCaps::MN_REQ_05_3_ConsistentValueByteCap;
  requirement consistentFieldCapReq
    : MN_REQ_00_MissionBridge::MN_REQ_05_HardCaps::MN_REQ_05_4_ConsistentFieldCap;
  requirement sessionCapEvictLruReq
    : MN_REQ_00_MissionBridge::MN_REQ_05_HardCaps::MN_REQ_05_5_SessionCapEvictLru;

  requirement processBoundaryReq
    : MN_REQ_00_MissionBridge::MN_REQ_06_ProcessBoundary;
  requirement inProcessPrimaryReq
    : MN_REQ_00_MissionBridge::MN_REQ_06_ProcessBoundary::MN_REQ_06_1_InProcessPrimary;
  requirement localIpcShareReq
    : MN_REQ_00_MissionBridge::MN_REQ_06_ProcessBoundary::MN_REQ_06_2_LocalIpcShare;
  requirement tcpServeMigrationReq
    : MN_REQ_00_MissionBridge::MN_REQ_06_ProcessBoundary::MN_REQ_06_3_TcpServeMigration;
  requirement durableStoreBehindMemNetReq
    : MN_REQ_00_MissionBridge::MN_REQ_06_ProcessBoundary::MN_REQ_06_4_DurableStoreBehindMemNet;
  requirement humanUsageLookReq
    : MN_REQ_00_MissionBridge::MN_REQ_06_ProcessBoundary::MN_REQ_06_5_HumanUsageLook;
  requirement deviceServicesOneDropletMcpReq
    : MN_REQ_00_MissionBridge::MN_REQ_06_ProcessBoundary::MN_REQ_06_6_DeviceServicesOneDropletMcp;
  requirement ssotToCodeAllocateReq
    : MN_REQ_00_MissionBridge::MN_REQ_06_ProcessBoundary::MN_REQ_06_7_SsotToCodeAllocate;
  requirement tipMemNetAccessPortalReq
    : MN_REQ_00_MissionBridge::MN_REQ_06_ProcessBoundary::MN_REQ_06_8_TipMemNetAccessPortal;
  requirement lanMcpFrontSeveralServesReq
    : MN_REQ_00_MissionBridge::MN_REQ_06_ProcessBoundary::MN_REQ_06_9_LanMcpFrontSeveralServes;
  requirement sliceHandCarryAcrossServesReq
    : MN_REQ_00_MissionBridge::MN_REQ_06_ProcessBoundary::MN_REQ_06_10_SliceHandCarryAcrossServes;
  requirement adminServeUsageReportReq
    : MN_REQ_00_MissionBridge::MN_REQ_06_ProcessBoundary::MN_REQ_06_11_AdminServeUsageReport;
  requirement productGatewayReq
    : MN_REQ_00_MissionBridge::MN_REQ_06_ProcessBoundary::MN_REQ_06_12_ProductGateway;
  requirement serveRequestIsolationReq
    : MN_REQ_00_MissionBridge::MN_REQ_06_ProcessBoundary::MN_REQ_06_13_ServeRequestIsolation;
  requirement safeServeUpgradeReq
    : MN_REQ_00_MissionBridge::MN_REQ_06_ProcessBoundary::MN_REQ_06_14_SafeServeUpgrade;
  requirement serveCheckpointReq
    : MN_REQ_00_MissionBridge::MN_REQ_06_ProcessBoundary::MN_REQ_06_15_ServeCheckpoint;
  requirement snapshotAclReq
    : MN_REQ_00_MissionBridge::MN_REQ_06_ProcessBoundary::MN_REQ_06_16_SnapshotAcl;

  requirement mcpAgentBoundaryReq
    : MN_REQ_00_MissionBridge::MN_REQ_07_McpAgentBoundary;
  requirement genericToolSurfaceReq
    : MN_REQ_00_MissionBridge::MN_REQ_07_McpAgentBoundary::MN_REQ_07_1_GenericToolSurface;
  requirement structuredToolEnvelopeReq
    : MN_REQ_00_MissionBridge::MN_REQ_07_McpAgentBoundary::MN_REQ_07_2_StructuredToolEnvelope;
  requirement noDomainProductToolsReq
    : MN_REQ_00_MissionBridge::MN_REQ_07_McpAgentBoundary::MN_REQ_07_3_NoDomainProductTools;
  requirement mcpLawSeedOnOpenReq
    : MN_REQ_00_MissionBridge::MN_REQ_07_McpAgentBoundary::MN_REQ_07_4_McpLawSeedOnOpen;
  requirement noStoreKeyToolSurfaceReq
    : MN_REQ_00_MissionBridge::MN_REQ_07_McpAgentBoundary::MN_REQ_07_5_NoStoreKeyToolSurface;

  requirement agentIoGrammarReq
    : MN_REQ_00_MissionBridge::MN_REQ_08_AgentIoGrammar;
  requirement llmFriendlyStdioReq
    : MN_REQ_00_MissionBridge::MN_REQ_08_AgentIoGrammar::MN_REQ_08_1_LlmFriendlyStdio;
  requirement llmFriendlyMcpReq
    : MN_REQ_00_MissionBridge::MN_REQ_08_AgentIoGrammar::MN_REQ_08_2_LlmFriendlyMcp;
  requirement noHostilePositionalDumpReq
    : MN_REQ_00_MissionBridge::MN_REQ_08_AgentIoGrammar::MN_REQ_08_3_NoHostilePositionalDump;
  requirement boundaryFriendlyIfInternalDiffersReq
    : MN_REQ_00_MissionBridge::MN_REQ_08_AgentIoGrammar::MN_REQ_08_4_BoundaryFriendlyIfInternalDiffers;
  requirement ioActorIsLlmReq
    : MN_REQ_00_MissionBridge::MN_REQ_08_AgentIoGrammar::MN_REQ_08_5_IoActorIsLlm;
  requirement followPromptRulesReq
    : MN_REQ_00_MissionBridge::MN_REQ_08_AgentIoGrammar::MN_REQ_08_6_FollowPromptRules;
  requirement writeApproxDisplayReq
    : MN_REQ_00_MissionBridge::MN_REQ_08_AgentIoGrammar::MN_REQ_08_7_WriteApproxDisplay;
  requirement templateCopyableShapesReq
    : MN_REQ_00_MissionBridge::MN_REQ_08_AgentIoGrammar::MN_REQ_08_8_TemplateCopyableShapes;
  requirement pinMapEmitSameAsMutateReq
    : MN_REQ_00_MissionBridge::MN_REQ_08_AgentIoGrammar::MN_REQ_08_9_PinMapEmitSameAsMutate;

  requirement humanInspectReq
    : MN_REQ_00_MissionBridge::MN_REQ_09_HumanInspect;
  requirement canonicalParserSsotReq
    : MN_REQ_00_MissionBridge::MN_REQ_09_HumanInspect::MN_REQ_09_1_CanonicalParserSsot;
  requirement rejectInvalidWireReq
    : MN_REQ_00_MissionBridge::MN_REQ_09_HumanInspect::MN_REQ_09_2_RejectInvalidWire;
  requirement parseFaithfulInspectReq
    : MN_REQ_00_MissionBridge::MN_REQ_09_HumanInspect::MN_REQ_09_3_ParseFaithfulInspect;
  requirement noAdHocConsumerSplitsReq
    : MN_REQ_00_MissionBridge::MN_REQ_09_HumanInspect::MN_REQ_09_4_NoAdHocConsumerSplits;
  requirement graphglotParseThenProductGateReq
    : MN_REQ_00_MissionBridge::MN_REQ_09_HumanInspect::MN_REQ_09_5_GraphGlotParseThenProductGate;

  requirement llmPropertiesAndLimitsReq
    : MN_REQ_00_MissionBridge::MN_REQ_10_LlmPropertiesAndLimits;
  requirement noChatAsDurableStoreReq
    : MN_REQ_00_MissionBridge::MN_REQ_10_LlmPropertiesAndLimits::MN_REQ_10_1_NoChatAsDurableStore;
  requirement pinMapMustFitContextReq
    : MN_REQ_00_MissionBridge::MN_REQ_10_LlmPropertiesAndLimits::MN_REQ_10_2_PinMapMustFitContext;
  requirement minimiseTokenRoundTripsReq
    : MN_REQ_00_MissionBridge::MN_REQ_10_LlmPropertiesAndLimits::MN_REQ_10_3_MinimiseTokenRoundTrips;
  requirement externalGroundTruthRequiredReq
    : MN_REQ_00_MissionBridge::MN_REQ_10_LlmPropertiesAndLimits::MN_REQ_10_4_ExternalGroundTruthRequired;
  requirement grammarMustBeLlmLearnableReq
    : MN_REQ_00_MissionBridge::MN_REQ_10_LlmPropertiesAndLimits::MN_REQ_10_5_GrammarMustBeLlmLearnable;
  requirement preferTemplateFriendlyPinsReq
    : MN_REQ_00_MissionBridge::MN_REQ_10_LlmPropertiesAndLimits::MN_REQ_10_6_PreferTemplateFriendlyPins;
  requirement humanVerifyViaParserReq
    : MN_REQ_00_MissionBridge::MN_REQ_10_LlmPropertiesAndLimits::MN_REQ_10_7_HumanVerifyViaParser;

  requirement snapshotInteropReq
    : MN_REQ_00_MissionBridge::MN_REQ_11_SnapshotInterop;
  requirement exportGraphToSysmlV2Req
    : MN_REQ_00_MissionBridge::MN_REQ_11_SnapshotInterop::MN_REQ_11_1_ExportGraphToSysmlV2;
  requirement nodeMapsToSysmlStructureReq
    : MN_REQ_00_MissionBridge::MN_REQ_11_SnapshotInterop::MN_REQ_11_2_NodeMapsToSysmlStructure;
  requirement edgeMapsToSysmlConnectionReq
    : MN_REQ_00_MissionBridge::MN_REQ_11_SnapshotInterop::MN_REQ_11_3_EdgeMapsToSysmlConnection;
  requirement distinctFromSessionSnapshotReq
    : MN_REQ_00_MissionBridge::MN_REQ_11_SnapshotInterop::MN_REQ_11_4_DistinctFromSessionSnapshot;
  requirement sysmlRoundTripShouldReq
    : MN_REQ_00_MissionBridge::MN_REQ_11_SnapshotInterop::MN_REQ_11_5_SysmlRoundTripShould;
  requirement snapshotCodebaseIntoGraphReq
    : MN_REQ_00_MissionBridge::MN_REQ_11_SnapshotInterop::MN_REQ_11_6_SnapshotCodebaseIntoGraph;
  requirement codebaseNodesAreModulesSymbolsReq
    : MN_REQ_00_MissionBridge::MN_REQ_11_SnapshotInterop::MN_REQ_11_7_CodebaseNodesAreModulesSymbols;
  requirement codebaseEdgesAreRelationsReq
    : MN_REQ_00_MissionBridge::MN_REQ_11_SnapshotInterop::MN_REQ_11_8_CodebaseEdgesAreRelations;
  requirement snapshotAtoIntoGraphReq
    : MN_REQ_00_MissionBridge::MN_REQ_11_SnapshotInterop::MN_REQ_11_9_SnapshotAtoIntoGraph;
  requirement snapshotSkillsAndRulesIntoGraphReq
    : MN_REQ_00_MissionBridge::MN_REQ_11_SnapshotInterop::MN_REQ_11_10_SnapshotSkillsAndRulesIntoGraph;
  requirement skillsAndRulesAreNodesReq
    : MN_REQ_00_MissionBridge::MN_REQ_11_SnapshotInterop::MN_REQ_11_11_SkillsAndRulesAreNodes;
  requirement skillsRulesEdgesAreRelationsReq
    : MN_REQ_00_MissionBridge::MN_REQ_11_SnapshotInterop::MN_REQ_11_12_SkillsRulesEdgesAreRelations;
  requirement mapOfPinsReq
    : MN_REQ_00_MissionBridge::MN_REQ_11_SnapshotInterop::MN_REQ_11_13_MapOfPins;
  requirement pcbaAtoNodesAreNetsComponentsPinsReq
    : MN_REQ_00_MissionBridge::MN_REQ_11_SnapshotInterop::MN_REQ_11_14_PcbaAtoNodesAreNetsComponentsPins;
  requirement pcbaAtoEdgesAreConnectivityReq
    : MN_REQ_00_MissionBridge::MN_REQ_11_SnapshotInterop::MN_REQ_11_15_PcbaAtoEdgesAreConnectivity;
  requirement pinIngestDeterministicIdsReq
    : MN_REQ_00_MissionBridge::MN_REQ_11_SnapshotInterop::MN_REQ_11_16_PinIngestDeterministicIds;
  requirement catalogModelSnapReq
    : MN_REQ_00_MissionBridge::MN_REQ_11_SnapshotInterop::MN_REQ_11_17_CatalogModelSnap;
  requirement crossCutSatisfyLocatorsReq
    : MN_REQ_00_MissionBridge::MN_REQ_11_SnapshotInterop::MN_REQ_11_17_CatalogModelSnap::MN_REQ_11_17_1_CrossCutSatisfyLocators;
  requirement snapSessionGrainReq
    : MN_REQ_00_MissionBridge::MN_REQ_11_SnapshotInterop::MN_REQ_11_17_CatalogModelSnap::MN_REQ_11_17_2_SnapSessionGrain;
  requirement snapBudgetPrecheckReq
    : MN_REQ_00_MissionBridge::MN_REQ_11_SnapshotInterop::MN_REQ_11_17_CatalogModelSnap::MN_REQ_11_17_3_SnapBudgetPrecheck;
  requirement snapCallerGoneRollbackReq
    : MN_REQ_00_MissionBridge::MN_REQ_11_SnapshotInterop::MN_REQ_11_17_CatalogModelSnap::MN_REQ_11_17_4_SnapCallerGoneRollback;
  requirement snapReplaceByModelIdentityReq
    : MN_REQ_00_MissionBridge::MN_REQ_11_SnapshotInterop::MN_REQ_11_17_CatalogModelSnap::MN_REQ_11_17_5_SnapReplaceByModelIdentity;

  requirement multitaskModeReq
    : MN_REQ_00_MissionBridge::MN_REQ_12_MultitaskMode;
  requirement sharedSessionMissionSsotReq
    : MN_REQ_00_MissionBridge::MN_REQ_12_MultitaskMode::MN_REQ_12_1_SharedSessionMissionSsot;
  requirement sharedStoreTransportReq
    : MN_REQ_00_MissionBridge::MN_REQ_12_MultitaskMode::MN_REQ_12_2_SharedStoreTransport;
  requirement parentOwnsTaskLifecycleReq
    : MN_REQ_00_MissionBridge::MN_REQ_12_MultitaskMode::MN_REQ_12_3_ParentOwnsTaskLifecycle;
  requirement workerPinMapAndScopedWriteReq
    : MN_REQ_00_MissionBridge::MN_REQ_12_MultitaskMode::MN_REQ_12_4_WorkerPinMapAndScopedWrite;
  requirement preferOneWorkerOrDisjointReq
    : MN_REQ_00_MissionBridge::MN_REQ_12_MultitaskMode::MN_REQ_12_5_PreferOneWorkerOrDisjoint;
  requirement parentEndTurnNoPollReq
    : MN_REQ_00_MissionBridge::MN_REQ_12_MultitaskMode::MN_REQ_12_6_ParentEndTurnNoPoll;
  requirement noAssumeAclReserveIngestReq
    : MN_REQ_00_MissionBridge::MN_REQ_12_MultitaskMode::MN_REQ_12_7_NoAssumeAclReserveIngest;
  requirement appliesToRelevantTasksReq
    : MN_REQ_00_MissionBridge::MN_REQ_12_MultitaskMode::MN_REQ_12_8_AppliesToRelevantTasks;
  requirement leadOwnsSessionImportReq
    : MN_REQ_00_MissionBridge::MN_REQ_12_MultitaskMode::MN_REQ_12_9_LeadOwnsSessionImport;
  requirement noChatOrWholeStoreImportReq
    : MN_REQ_00_MissionBridge::MN_REQ_12_MultitaskMode::MN_REQ_12_10_NoChatOrWholeStoreImport;
  requirement cheapLlmImportGuardSoftReq
    : MN_REQ_00_MissionBridge::MN_REQ_12_MultitaskMode::MN_REQ_12_11_CheapLlmImportGuardSoft;
  requirement hostDrivenAsyncParallelReq
    : MN_REQ_00_MissionBridge::MN_REQ_12_MultitaskMode::MN_REQ_12_12_HostDrivenAsyncParallel;
  requirement neighbourhoodReserveReq
    : MN_REQ_00_MissionBridge::MN_REQ_12_MultitaskMode::MN_REQ_12_13_NeighbourhoodReserve;

  requirement recallCommitReq
    : MN_REQ_00_MissionBridge::MN_REQ_13_RecallCommit;
  requirement twoOperatorsReq
    : MN_REQ_00_MissionBridge::MN_REQ_13_RecallCommit::MN_REQ_13_1_TwoOperators;
  requirement sameThingAbsorbReq
    : MN_REQ_00_MissionBridge::MN_REQ_13_RecallCommit::MN_REQ_13_2_SameThingAbsorb;

  requirement atelierBoardAsksReq
    : MN_REQ_00_MissionBridge::MN_REQ_14_AtelierBoardAsks;
  requirement whereRangeComparisonReq
    : MN_REQ_00_MissionBridge::MN_REQ_14_AtelierBoardAsks::MN_REQ_14_1_WhereRangeComparison;
  requirement pagedReadsPastCapReq
    : MN_REQ_00_MissionBridge::MN_REQ_14_AtelierBoardAsks::MN_REQ_14_2_PagedReadsPastCap;
  requirement typedDirectedWalksReq
    : MN_REQ_00_MissionBridge::MN_REQ_14_AtelierBoardAsks::MN_REQ_14_3_TypedDirectedWalks;
  requirement idIndexAndLinearLoadReq
    : MN_REQ_00_MissionBridge::MN_REQ_14_AtelierBoardAsks::MN_REQ_14_4_IdIndexAndLinearLoad;
  requirement raisableSessionRecordCapReq
    : MN_REQ_00_MissionBridge::MN_REQ_14_AtelierBoardAsks::MN_REQ_14_5_RaisableSessionRecordCap;

  requirement idDesignReq
    : MN_REQ_00_MissionBridge::MN_REQ_14_AtelierBoardAsks::MN_REQ_14_6_IdDesign;
  requirement agentHandlesNotIdsReq
    : MN_REQ_00_MissionBridge::MN_REQ_14_AtelierBoardAsks::MN_REQ_14_7_AgentHandlesNotIds;
  requirement developerSurfaceRealIdsReq
    : MN_REQ_00_MissionBridge::MN_REQ_14_AtelierBoardAsks::MN_REQ_14_8_DeveloperSurfaceRealIds;
  requirement valueCap32kReq
    : MN_REQ_00_MissionBridge::MN_REQ_14_AtelierBoardAsks::MN_REQ_14_9_ValueCap32k;
  requirement sessionTotalBytesCapReq
    : MN_REQ_00_MissionBridge::MN_REQ_14_AtelierBoardAsks::MN_REQ_14_10_SessionTotalBytesCap;
  requirement bypassPathCapsReq
    : MN_REQ_00_MissionBridge::MN_REQ_14_AtelierBoardAsks::MN_REQ_14_11_BypassPathCaps;
  requirement incrementalByteBudgetReq
    : MN_REQ_00_MissionBridge::MN_REQ_14_AtelierBoardAsks::MN_REQ_14_12_IncrementalByteBudget;
  requirement pagingCursorReq
    : MN_REQ_00_MissionBridge::MN_REQ_14_AtelierBoardAsks::MN_REQ_14_13_PagingCursor;

  // Groups derive from mission (MN-REQ-00)
  #derivation connection deriveGroupsFromMission {
    end #original ::> missionReq;
    end #derive ::> sessionLifecycleReq;
    end #derive ::> memoryNetGraphReq;
    end #derive ::> strictMutateReq;
    end #derive ::> sliceEconomyReq;
    end #derive ::> hardCapsReq;
    end #derive ::> processBoundaryReq;
    end #derive ::> mcpAgentBoundaryReq;
    end #derive ::> agentIoGrammarReq;
    end #derive ::> humanInspectReq;
    end #derive ::> llmPropertiesAndLimitsReq;
    end #derive ::> snapshotInteropReq;
    end #derive ::> multitaskModeReq;
    end #derive ::> recallCommitReq;
  }

  // Leaves derive from their group
  #derivation connection deriveSessionLeaves {
    end #original ::> sessionLifecycleReq;
    end #derive ::> namedSessionsReq;
    end #derive ::> sessionLifecycleOpsReq;
    end #derive ::> sessionTtlAndCapsReq;
    end #derive ::> saveSessionSnapshotReq;
    end #derive ::> loadSessionSnapshotReq;
    end #derive ::> optionalKeepSessionIdReq;
    end #derive ::> sessionAsSsotHandleReq;
    end #derive ::> noGraphDumpHandoffReq;
    end #derive ::> snapshotLosslessRoundTripReq;
    end #derive ::> sessionLifecycleAclWhoReq;
  }

  #derivation connection deriveMemoryNetGraphLeaves {
    end #original ::> memoryNetGraphReq;
    end #derive ::> exactlyNodeAndEdgeReq;
    end #derive ::> nodesHoldAtomisedFactsReq;
    end #derive ::> edgesAreFirstClassReq;
    end #derive ::> queryOverNodeEdgeGraphReq;
    end #derive ::> grammarExpressesNodeAndEdgeReq;
    end #derive ::> parserRecoversNodeAndEdgeReq;
    end #derive ::> schemaValidatedIngestReq;
    end #derive ::> idNotRequiredOnWireReq;
    end #derive ::> noCopyCousinStoreKeyReq;
  }

  #derivation connection deriveStrictMutateLeaves {
    end #original ::> strictMutateReq;
    end #derive ::> addFailsIfExistsReq;
    end #derive ::> updateFailsIfAbsentReq;
    end #derive ::> noSilentUpsertReq;
    end #derive ::> honourWherePredicateReq;
  }

  #derivation connection deriveSliceEconomyLeaves {
    end #original ::> sliceEconomyReq;
    end #derive ::> anchoredPinMapReq;
    end #derive ::> recycleHiddenFromPinMapReq;
    end #derive ::> pinMapDepthAndRowCapsReq;
    end #derive ::> engineLawPrependReq;
    end #derive ::> anchoredWalkReq;
    end #derive ::> boundedMatchFindReq;
    end #derive ::> relativeSeedThenShapeWalkReq;
    end #derive ::> cueMultiRootHonestReq;
    end #derive ::> sessionOutlineEmptyCueReq;
    end #derive ::> peakLLastResortReq;
    end #derive ::> pinMapOrderFromObservablesReq;
  }

  #derivation connection deriveHardCapsLeaves {
    end #original ::> hardCapsReq;
    end #derive ::> storeResourceCapsReq;
    end #derive ::> queryFanoutCapsReq;
    end #derive ::> consistentValueByteCapReq;
    end #derive ::> consistentFieldCapReq;
    end #derive ::> sessionCapEvictLruReq;
  }

  #derivation connection deriveSessionCapEvictFromCapsAndSnapshot {
    end #original ::> sessionTtlAndCapsReq;
    end #original ::> snapshotLosslessRoundTripReq;
    end #original ::> snapshotAclReq;
    end #derive ::> sessionCapEvictLruReq;
  }

  #derivation connection deriveProcessBoundaryLeaves {
    end #original ::> processBoundaryReq;
    end #derive ::> inProcessPrimaryReq;
    end #derive ::> localIpcShareReq;
    end #derive ::> tcpServeMigrationReq;
    end #derive ::> durableStoreBehindMemNetReq;
    end #derive ::> humanUsageLookReq;
    end #derive ::> deviceServicesOneDropletMcpReq;
    end #derive ::> ssotToCodeAllocateReq;
    end #derive ::> tipMemNetAccessPortalReq;
    end #derive ::> lanMcpFrontSeveralServesReq;
    end #derive ::> sliceHandCarryAcrossServesReq;
    end #derive ::> adminServeUsageReportReq;
    end #derive ::> productGatewayReq;
  }

  #derivation connection deriveMcpLeaves {
    end #original ::> mcpAgentBoundaryReq;
    end #derive ::> genericToolSurfaceReq;
    end #derive ::> structuredToolEnvelopeReq;
    end #derive ::> noDomainProductToolsReq;
    end #derive ::> mcpLawSeedOnOpenReq;
    end #derive ::> noStoreKeyToolSurfaceReq;
  }

  #derivation connection deriveAgentIoLeaves {
    end #original ::> agentIoGrammarReq;
    end #derive ::> llmFriendlyStdioReq;
    end #derive ::> llmFriendlyMcpReq;
    end #derive ::> noHostilePositionalDumpReq;
    end #derive ::> boundaryFriendlyIfInternalDiffersReq;
    end #derive ::> ioActorIsLlmReq;
    end #derive ::> followPromptRulesReq;
    end #derive ::> writeApproxDisplayReq;
    end #derive ::> templateCopyableShapesReq;
    end #derive ::> pinMapEmitSameAsMutateReq;
  }

  #derivation connection deriveHumanInspectLeaves {
    end #original ::> humanInspectReq;
    end #derive ::> canonicalParserSsotReq;
    end #derive ::> rejectInvalidWireReq;
    end #derive ::> parseFaithfulInspectReq;
    end #derive ::> noAdHocConsumerSplitsReq;
  }

  #derivation connection deriveLlmLimitLeaves {
    end #original ::> llmPropertiesAndLimitsReq;
    end #derive ::> noChatAsDurableStoreReq;
    end #derive ::> pinMapMustFitContextReq;
    end #derive ::> minimiseTokenRoundTripsReq;
    end #derive ::> externalGroundTruthRequiredReq;
    end #derive ::> grammarMustBeLlmLearnableReq;
    end #derive ::> preferTemplateFriendlyPinsReq;
    end #derive ::> humanVerifyViaParserReq;
  }

  #derivation connection deriveSnapshotInteropLeaves {
    end #original ::> snapshotInteropReq;
    end #derive ::> mapOfPinsReq;
    end #derive ::> exportGraphToSysmlV2Req;
    end #derive ::> nodeMapsToSysmlStructureReq;
    end #derive ::> edgeMapsToSysmlConnectionReq;
    end #derive ::> distinctFromSessionSnapshotReq;
    end #derive ::> sysmlRoundTripShouldReq;
    end #derive ::> snapshotCodebaseIntoGraphReq;
    end #derive ::> codebaseNodesAreModulesSymbolsReq;
    end #derive ::> codebaseEdgesAreRelationsReq;
    end #derive ::> snapshotAtoIntoGraphReq;
    end #derive ::> snapshotSkillsAndRulesIntoGraphReq;
    end #derive ::> skillsAndRulesAreNodesReq;
    end #derive ::> skillsRulesEdgesAreRelationsReq;
    end #derive ::> pcbaAtoNodesAreNetsComponentsPinsReq;
    end #derive ::> pcbaAtoEdgesAreConnectivityReq;
    end #derive ::> pinIngestDeterministicIdsReq;
    end #derive ::> catalogModelSnapReq;
    end #derive ::> crossCutSatisfyLocatorsReq;
    end #derive ::> snapSessionGrainReq;
    end #derive ::> snapBudgetPrecheckReq;
    end #derive ::> snapCallerGoneRollbackReq;
    end #derive ::> snapReplaceByModelIdentityReq;
  }

  #derivation connection deriveMultitaskLeaves {
    end #original ::> multitaskModeReq;
    end #derive ::> sharedSessionMissionSsotReq;
    end #derive ::> sharedStoreTransportReq;
    end #derive ::> parentOwnsTaskLifecycleReq;
    end #derive ::> workerPinMapAndScopedWriteReq;
    end #derive ::> preferOneWorkerOrDisjointReq;
    end #derive ::> parentEndTurnNoPollReq;
    end #derive ::> noAssumeAclReserveIngestReq;
    end #derive ::> appliesToRelevantTasksReq;
    end #derive ::> leadOwnsSessionImportReq;
    end #derive ::> noChatOrWholeStoreImportReq;
    end #derive ::> cheapLlmImportGuardSoftReq;
    end #derive ::> hostDrivenAsyncParallelReq;
    end #derive ::> neighbourhoodReserveReq;
  }

  #derivation connection deriveRecallCommitLeaves {
    end #original ::> recallCommitReq;
    end #derive ::> twoOperatorsReq;
    end #derive ::> sameThingAbsorbReq;
  }

  #derivation connection deriveSameThingFromCueHonesty {
    end #original ::> cueMultiRootHonestReq;
    end #original ::> twoOperatorsReq;
    end #derive ::> sameThingAbsorbReq;
  }

  #derivation connection deriveOutlineFromRecallHonesty {
    end #original ::> relativeSeedThenShapeWalkReq;
    end #original ::> twoOperatorsReq;
    end #derive ::> sessionOutlineEmptyCueReq;
  }

  #derivation connection derivePeakFromRecallHonesty {
    end #original ::> relativeSeedThenShapeWalkReq;
    end #original ::> twoOperatorsReq;
    end #derive ::> peakLLastResortReq;
  }

  #derivation connection deriveTargetsFromMapOfPins {
    end #original ::> mapOfPinsReq;
    end #derive ::> exportGraphToSysmlV2Req;
    end #derive ::> snapshotCodebaseIntoGraphReq;
    end #derive ::> snapshotAtoIntoGraphReq;
    end #derive ::> snapshotSkillsAndRulesIntoGraphReq;
  }

  // Cross-derive: LLM limitations -> AgentIO / inspect / session / slice
  #derivation connection deriveAgentIoFromLlmLimits {
    end #original ::> grammarMustBeLlmLearnableReq;
    end #original ::> preferTemplateFriendlyPinsReq;
    end #original ::> minimiseTokenRoundTripsReq;
    end #derive ::> followPromptRulesReq;
    end #derive ::> ioActorIsLlmReq;
    end #derive ::> writeApproxDisplayReq;
    end #derive ::> templateCopyableShapesReq;
    end #derive ::> pinMapEmitSameAsMutateReq;
    end #derive ::> noHostilePositionalDumpReq;
  }

  #derivation connection derivePromptSurfaceFromPromptRules {
    end #original ::> followPromptRulesReq;
    end #derive ::> llmFriendlyStdioReq;
    end #derive ::> llmFriendlyMcpReq;
    end #derive ::> writeApproxDisplayReq;
    end #derive ::> templateCopyableShapesReq;
    end #derive ::> pinMapEmitSameAsMutateReq;
  }

  #derivation connection deriveSessionFromNoChatStore {
    end #original ::> noChatAsDurableStoreReq;
    end #derive ::> sessionLifecycleReq;
  }

  #derivation connection deriveSaveLoadFromNoChatStore {
    end #original ::> noChatAsDurableStoreReq;
    end #derive ::> saveSessionSnapshotReq;
    end #derive ::> loadSessionSnapshotReq;
  }

  #derivation connection deriveKeepIdFromLoad {
    end #original ::> loadSessionSnapshotReq;
    end #derive ::> optionalKeepSessionIdReq;
  }

  #derivation connection deriveSliceFromContextLimit {
    end #original ::> pinMapMustFitContextReq;
    end #derive ::> sliceEconomyReq;
    end #derive ::> hardCapsReq;
  }

  #derivation connection deriveFactsFromGroundTruth {
    end #original ::> externalGroundTruthRequiredReq;
    end #derive ::> memoryNetGraphReq;
    end #derive ::> strictMutateReq;
  }

  #derivation connection deriveInspectFromHumanVerify {
    end #original ::> humanVerifyViaParserReq;
    end #derive ::> humanInspectReq;
    end #derive ::> parserRecoversNodeAndEdgeReq;
  }

  #derivation connection deriveIoFromNodeEdgeGrammar {
    end #original ::> grammarExpressesNodeAndEdgeReq;
    end #derive ::> agentIoGrammarReq;
    end #derive ::> followPromptRulesReq;
  }

  #derivation connection deriveSliceFromNodeEdgeQuery {
    end #original ::> queryOverNodeEdgeGraphReq;
    end #derive ::> sliceEconomyReq;
  }

  #derivation connection deriveRecallFromSlice {
    end #original ::> queryOverNodeEdgeGraphReq;
    end #original ::> sliceEconomyReq;
    end #derive ::> recallCommitReq;
    end #derive ::> twoOperatorsReq;
    end #derive ::> sameThingAbsorbReq;
    end #derive ::> sessionOutlineEmptyCueReq;
  }

  #derivation connection deriveSnapshotFromNodeEdge {
    end #original ::> exactlyNodeAndEdgeReq;
    end #original ::> edgesAreFirstClassReq;
    end #derive ::> snapshotInteropReq;
    end #derive ::> exportGraphToSysmlV2Req;
    end #derive ::> snapshotCodebaseIntoGraphReq;
    end #derive ::> snapshotAtoIntoGraphReq;
    end #derive ::> snapshotSkillsAndRulesIntoGraphReq;
  }

  #derivation connection deriveSysmlMappingFromNodeEdge {
    end #original ::> exactlyNodeAndEdgeReq;
    end #derive ::> nodeMapsToSysmlStructureReq;
    end #derive ::> edgeMapsToSysmlConnectionReq;
  }

  #derivation connection deriveCodebaseShapeFromNodeEdge {
    end #original ::> nodesHoldAtomisedFactsReq;
    end #original ::> edgesAreFirstClassReq;
    end #derive ::> codebaseNodesAreModulesSymbolsReq;
    end #derive ::> codebaseEdgesAreRelationsReq;
  }

  #derivation connection deriveSkillsRulesShapeFromNodeEdge {
    end #original ::> nodesHoldAtomisedFactsReq;
    end #original ::> edgesAreFirstClassReq;
    end #derive ::> skillsAndRulesAreNodesReq;
    end #derive ::> skillsRulesEdgesAreRelationsReq;
  }

  #derivation connection derivePcbaAtoShapeFromNodeEdge {
    end #original ::> nodesHoldAtomisedFactsReq;
    end #original ::> edgesAreFirstClassReq;
    end #derive ::> pcbaAtoNodesAreNetsComponentsPinsReq;
    end #derive ::> pcbaAtoEdgesAreConnectivityReq;
  }

  #derivation connection deriveDistinctFromSessionSave {
    end #original ::> saveSessionSnapshotReq;
    end #original ::> loadSessionSnapshotReq;
    end #derive ::> distinctFromSessionSnapshotReq;
  }

  // Cross-derive: Multitask from no-chat-store, process boundary, pin map
  #derivation connection deriveMultitaskFromNoChatStore {
    end #original ::> noChatAsDurableStoreReq;
    end #derive ::> multitaskModeReq;
    end #derive ::> sharedSessionMissionSsotReq;
    end #derive ::> sessionAsSsotHandleReq;
    end #derive ::> noGraphDumpHandoffReq;
    end #derive ::> leadOwnsSessionImportReq;
    end #derive ::> noChatOrWholeStoreImportReq;
    end #derive ::> cheapLlmImportGuardSoftReq;
  }

  #derivation connection deriveMultitaskFromProcessBoundary {
    end #original ::> processBoundaryReq;
    end #original ::> localIpcShareReq;
    end #original ::> tcpServeMigrationReq;
    end #derive ::> sharedStoreTransportReq;
  }

  #derivation connection deriveHumanUsageLookFromServeAndCaps {
    end #original ::> tcpServeMigrationReq;
    end #original ::> sessionTtlAndCapsReq;
    end #original ::> storeResourceCapsReq;
    end #original ::> genericToolSurfaceReq;
    end #derive ::> humanUsageLookReq;
  }

  #derivation connection deriveAdminServeUsageFromServeAndCaps {
    end #original ::> tcpServeMigrationReq;
    end #original ::> sessionTtlAndCapsReq;
    end #original ::> storeResourceCapsReq;
    end #original ::> noDomainProductToolsReq;
    end #derive ::> adminServeUsageReportReq;
  }

  #derivation connection deriveWorkerFromPinMap {
    end #original ::> anchoredPinMapReq;
    end #derive ::> workerPinMapAndScopedWriteReq;
  }

  #derivation connection deriveNoAssumeFromIngestRoadmap {
    end #original ::> pinIngestDeterministicIdsReq;
    end #derive ::> noAssumeAclReserveIngestReq;
  }

  // Atelier-board asks (PROPOSAL): groups derive from mission; leaves from existing rules
  #derivation connection deriveAtelierBoardAsksFromMission {
    end #original ::> missionReq;
    end #derive ::> atelierBoardAsksReq;
    end #derive ::> whereRangeComparisonReq;
    end #derive ::> pagedReadsPastCapReq;
    end #derive ::> typedDirectedWalksReq;
    end #derive ::> idIndexAndLinearLoadReq;
    end #derive ::> raisableSessionRecordCapReq;
    end #derive ::> idDesignReq;
    end #derive ::> agentHandlesNotIdsReq;
    end #derive ::> developerSurfaceRealIdsReq;
    end #derive ::> valueCap32kReq;
    end #derive ::> sessionTotalBytesCapReq;
  }

  #derivation connection deriveWhereRangeFromWhereHonest {
    end #original ::> honourWherePredicateReq;
    end #derive ::> whereRangeComparisonReq;
  }

  #derivation connection deriveRecordCapFromIndexAndCaps {
    end #original ::> storeResourceCapsReq;
    end #original ::> idIndexAndLinearLoadReq;
    end #derive ::> raisableSessionRecordCapReq;
  }

  #derivation connection deriveIdDesignFromIdIndex {
    end #original ::> idIndexAndLinearLoadReq;
    end #original ::> idNotRequiredOnWireReq;
    end #original ::> noCopyCousinStoreKeyReq;
    end #derive ::> idDesignReq;
  }

  // 14.7 also traces to the owner decision 2026-11-02 (handles only for the
  // LLM-facing MCP surface; real ids on the developer surface, 14.8).
  #derivation connection deriveAgentHandlesFromIdDesign {
    end #original ::> idDesignReq;
    end #derive ::> agentHandlesNotIdsReq;
  }

  #derivation connection deriveDeveloperSurfaceFromIdDesign {
    end #original ::> idDesignReq;
    end #derive ::> developerSurfaceRealIdsReq;
  }

  #derivation connection deriveValueCapFromStoreCaps {
    end #original ::> storeResourceCapsReq;
    end #derive ::> valueCap32kReq;
  }

  #derivation connection deriveTotalBytesCapFromCaps {
    end #original ::> storeResourceCapsReq;
    end #original ::> raisableSessionRecordCapReq;
    end #original ::> valueCap32kReq;
    end #derive ::> sessionTotalBytesCapReq;
  }

  #derivation connection deriveIncrementalBudgetFromTotalBytesCap {
    end #original ::> sessionTotalBytesCapReq;
    end #original ::> bypassPathCapsReq;
    end #derive ::> incrementalByteBudgetReq;
  }
}
